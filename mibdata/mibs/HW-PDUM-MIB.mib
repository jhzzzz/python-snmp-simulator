--
-- HW_SMM_PDUM.mib
-- MIB generated by MG-SOFT Visual MIB Builder Version 4.0 Build 349
-- Wednesday, July 31, 2013 at 14:32:30
--

-- /****************************************************************************
-- 
-- Copyright (C), 2004-2011, Huawei Tech. Co., Ltd.
-- 
-- *****************************************************************************
-- File Name     : HW-Blade-MIB.mib
-- Version       : Initial Draft
-- Author        : liangguixiang
-- Created       : 2005-7-18
-- Last Modified : 
-- Description   : MIB definitions for hwBlade module
-- 
-- ****************************************************************************/

	HW-PDUM-MIB DEFINITIONS ::= BEGIN
 
		IMPORTS
			OBJECT-GROUP			
				FROM SNMPv2-CONF			
			enterprises, Integer32, OBJECT-TYPE, MODULE-IDENTITY			
				FROM SNMPv2-SMI;
	
	
		-- 1.3.6.1.4.1.2011.2.82.1.101.1
		hwPDUSmm MODULE-IDENTITY 
			LAST-UPDATED "190607070000Z"		-- July 07, 1906 at 00:00 GMT
			ORGANIZATION 
				"OSCA Soft Group"
			CONTACT-INFO 
				"Huawei Technologies Co."
			DESCRIPTION 
				"The MIB module for stub module hwBlade."
			::= { hwPDU 1 }

		
	
--
-- Node definitions
--
	
		-- 1.3.6.1.4.1.2011
		huawei OBJECT IDENTIFIER ::= { enterprises 2011 }

		
		-- 1.3.6.1.4.1.2011.2
		products OBJECT IDENTIFIER ::= { huawei 2 }

		
		-- 1.3.6.1.4.1.2011.2.82
		hwOSTA OBJECT IDENTIFIER ::= { products 82 }

		
		-- 1.3.6.1.4.1.2011.2.82.1
		hwUSP OBJECT IDENTIFIER ::= { hwOSTA 1 }

		
		-- 1.3.6.1.4.1.2011.2.82.1.101
		hwPDU OBJECT IDENTIFIER ::= { hwUSP 101 }

		
		-- 1.3.6.1.4.1.2011.2.82.1.101.1.1
		hwPDUNode OBJECT-GROUP
			OBJECTS { hwSoftVersion, hwPduLinkStatus, hwPduVersion, hwBuzzerSw, hwMonitorStatus, 
				hwLoadProc, hwLoadFile, hwBase2Status, hwBase1Status, hwPduLoadProc, 
				hwPduLoadFile, hwAllLoadFile, hwAllLoadProc, hwPduResetReason, hwPduConfigData, 
				hwPduWarningMask, hwPduAnalog, hwPduWarningStatus, hwPduLinkStatusNode, hwPduLinkStatusIndex, 
				hwPduVersionIndex, hwPduVersioNode, hwPduConfigDataIndex, hwPduConfigDataNode, hwPduWarningMaskIndex, 
				hwPduWarningMaskNode, hwPduAnalogIndex, hwPduAnalogNode, hwBuzzerSwIndex, hwBuzzerSwNode, 
				hwPduResetReasoIndex, hwPduResetReasonNode, hwPduWarningStatusIndex, hwPduWarningStatusNode, hwSmmVer, 
				hwPdumReset, hwBladeVerIndex, hwBladeVerNode, hwAllLoadMulProc, hwPdumDebug, 
				bladeverion, versionindex, hwPdumTrapIpAddr, hwSmmInfo, hwPduAlmsNode, 
				hwPduAlmsIndex, hwPduEidNode, hwPduEidIndex }
			STATUS deprecated
			DESCRIPTION 
				"Description."
			::= { hwPDUSmm 1 }

		
		-- 1.3.6.1.4.1.2011.2.82.1.101.1.2
		hwPDUM OBJECT IDENTIFIER ::= { hwPDUSmm 2 }

		
-- 配电管理模块版本查询接口,字符串，只读：
-- 例:1.O
-- 
		-- 1.3.6.1.4.1.2011.2.82.1.101.1.2.1
		hwSoftVersion OBJECT-TYPE
			SYNTAX OCTET STRING (SIZE (0..512))
			MAX-ACCESS read-only
			STATUS deprecated
			DESCRIPTION
				"Pdu Manager SoftWare Version"
			::= { hwPDUM 1 }

		
-- 配电模块串口链接状态，只读,字符串表示
-- 仅有下面两种状态:
-- UP
-- Down
-- 
-- 例如:
-- Down
-- 表示目前配电框同SMM板通信中断，需要告警处理。
		-- 1.3.6.1.4.1.2011.2.82.1.101.1.2.2
		hwPduLinkStatus OBJECT-TYPE
			SYNTAX OCTET STRING (SIZE (0..512))
			MAX-ACCESS read-only
			STATUS deprecated
			DESCRIPTION
				"Serial Link Status: SMM - PDU"
			DEFVAL { "" }
			::= { hwPDUM 2 }
-- 0 link up 
-- 1 link down
		
-- 配电框版本信息，只读
-- 软件主版本号 
-- 软件副版本号 
-- PCB版本号
-- 可编程器件版本号
-- 编译时间 年月日
-- 
-- 例如:2 0 1 1 7 6 27 
-- 表示:软件主版本2，副版本0，PCB版本为1，可编程器件版本1，
-- 编译时间为 07 年 6月 27日
		-- 1.3.6.1.4.1.2011.2.82.1.101.1.2.3
		hwPduVersion OBJECT-TYPE
			SYNTAX OCTET STRING (SIZE (0..512))
			MAX-ACCESS read-only
			STATUS deprecated
			DESCRIPTION
				"The version of PDU"
			::= { hwPDUM 3 }

		
-- 核心网配电框配置数据定义，由下面各个字段定义
-- 可读写，空格区分，每个参数含义如下：
-- （先获取默认值，再修改即可）
-- 
-- 6路电压值: 上限 下限
-- 4路外接开关量传感器：L/H 
-- L表示低电平正常，H表示高电平正常
-- 
-- 示例如下:
-- 58 42 58 42 58 42 58 42 58 42 58 42 L L L L 
-- 表示各路电源上限为58，下限为42，传感器均为电平低正常。
-- 
-- 当前版本默认值：
-- 电压默认是: 上限 58  下限 42，
-- 4个传感器默认:低电平为正常 L
		-- 1.3.6.1.4.1.2011.2.82.1.101.1.2.4
		hwPduConfigData OBJECT-TYPE
			SYNTAX OCTET STRING (SIZE (0..512))
			MAX-ACCESS read-write
			STATUS deprecated
			DESCRIPTION
				"Get/Set config data of pdu
				
				16-channel voltage value: Upperlimit Lowerlimit
				4-channel external switch sensor: L/H
				Board temperature sensor: Upperlimit Lowerlimit
				"
			::= { hwPDUM 4 }

		
-- 告警屏蔽/使能状态设置及查询操作，各个字段对应含义解析
-- 如下，使用空格区分：
-- 
-- 6路电源告警： ON/OFF
-- 20路输出开关量传感器告警：ON/OFF
-- 4路外接开关量传感器告警：ON/OFF
-- 
-- 
-- 示例如下:
-- ON ON ON ON ON ON ON ON ON ON ON ON ON ON ON ON ON ON ON ON ON ON ON ON ON ON ON ON ON ON 
-- 
-- 默认配电框状态为 ON
-- 
		-- 1.3.6.1.4.1.2011.2.82.1.101.1.2.5
		hwPduWarningMask OBJECT-TYPE
			SYNTAX OCTET STRING (SIZE (0..512))
			MAX-ACCESS read-write
			STATUS deprecated
			DESCRIPTION
				"Get/Set PDU alarm enable
				
				16-channel input voltage alarm: ON/OFF
				16-channel output switch sensor: ON/OFF
				4-channel external switch sensor: ON/OFF
				Two device fault: ON/OFF
				A board temperature sensor: ON/OFF
				
				For example: ON ON ON ON ON ON ON ON ON ON ON ON ON ON ON ON ON ON ON ON ON ON ON ON ON ON ON ON ON ON ON ON ON ON ON ON ON ON ON
				
				If input less than 39 alarm mask, the system configuration of the front part of the mask, the latter part remains unchanged.
				If input more than 39 alarm mask, the portion of the greater than 39 does not handle."
			::= { hwPDUM 5 }

		
-- 获取配电框模拟量数据值，6路电源电压值，空格区分，只读：
-- 
-- 例如:
-- 53 53 53 53 53 53
		-- 1.3.6.1.4.1.2011.2.82.1.101.1.2.6
		hwPduAnalog OBJECT-TYPE
			SYNTAX OCTET STRING (SIZE (0..512))
			MAX-ACCESS read-only
			STATUS deprecated
			DESCRIPTION
				"Get analog value of PDU.
				
				It contain 16-channel voltage value and a board temperature sensor value"
			::= { hwPDUM 6 }

		
-- 蜂鸣器控制及状态接口，字符串控制，可读写
-- ON/OFF
-- 
-- 蜂鸣器默认：关闭 OFF
-- 
-- 
-- 例如:
-- Operation: Get
-- Request binding:
-- 1: hwBuzzerSw.0 (null) null
-- Response binding:
-- 1: hwBuzzerSw.0 (octet string) OFF
-- 
		-- 1.3.6.1.4.1.2011.2.82.1.101.1.2.7
		hwBuzzerSw OBJECT-TYPE
			SYNTAX OCTET STRING
			MAX-ACCESS read-write
			STATUS deprecated
			DESCRIPTION
				"Get/Set buzzer switch: ON/OFF"
			DEFVAL { "on" }
			::= { hwPDUM 7 }

		
-- 获取配电框上次复位原因,字符串描述。
-- 软件可以不做解析，直接显示处理。
-- 
-- 例如:
-- Communicate Failed Reset
		-- 1.3.6.1.4.1.2011.2.82.1.101.1.2.8
		hwPduResetReason OBJECT-TYPE
			SYNTAX OCTET STRING (SIZE (0..512))
			MAX-ACCESS read-only
			STATUS deprecated
			DESCRIPTION
				"Description.   
				   00H：Powered On
				   01H：Manual Reset；
				   02H：Command Reset；
				   03H：Communication Failed；
				   04H：Hardware Fault
				"
			::= { hwPDUM 8 }

		
-- 告警状态查询，字符串描述各个告警信息:
-- 
-- 
-- 例如：
-- OK OK OK OK OK OK OK OK OK OK OK OK OK OK OK OK OK OK OK OK OK OK OK OK OK OK ALM ALM ALM ALM
-- 表示6路电源，20路开关均正常，4路开关量传感器告警。
-- 
-- 另trap告警,使用TRAP id来区分不同的告警状态，OID均对应该节点OID。
-- 其中偶数表示告警的产生，+1奇数表示告警消除；
-- 其中有些告警为不可消除的事件告警，需要区分处理。
-- 
-- 定义如下:
-- 0	一般事件	清空所有该OID(配电框)告警信息，重新下发配电框配置数据及告警屏蔽操作。	配电框复位/启动，恢复所有配电框告警信息，需要重新下发配电框配置。
-- 1			
-- 2	严重告警	无	配电框通信故障
-- 3	恢复	无	串口链路恢复正常
-- 4	一般告警	无	配电框自检失败
-- 			
-- 			
-- 			
-- 			
-- 			
-- 			
-- 			
-- 			
-- 100	一般告警		第一路-48V电压过高告警
-- 101			告警恢复
-- 102	一般告警		第一路-48V电压过低告警
-- 103			告警恢复
-- 104	一般告警		第二路-48V电压过高告警
-- 105			告警恢复
-- 106	一般告警		第二路-48V电压过低告警
-- 107			告警恢复
-- 108	一般告警		第三路-48V电压过高告警
-- 109			告警恢复
-- 110	一般告警		第三路-48V电压过低告警
-- 111			告警恢复
-- 112	一般告警		第四路-48V电压过高告警
-- 113			告警恢复
-- 114	一般告警		第四路-48V电压过低告警
-- 115			告警恢复
-- 116	一般告警		第五路-48V电压过高告警
-- 117			告警恢复
-- 118	一般告警		第五路-48V电压过低告警
-- 119			告警恢复
-- 120	一般告警		第六路-48V电压过高告警
-- 121			告警恢复
-- 122	一般告警		第六路-48V电压过低告警
-- 123			告警恢复
-- 			
-- 			
-- 150	一般告警		第1路输出控制开关告警
-- 151			告警恢复
-- 152	一般告警		第2路输出控制开关告警
-- 153			告警恢复
-- 154	一般告警		第3路输出控制开关告警
-- 155			告警恢复
-- 156	一般告警		第4路输出控制开关告警
-- 157			告警恢复
-- 158	一般告警		第5路输出控制开关告警
-- 159			告警恢复
-- 160	一般告警		第6路输出控制开关告警
-- 161			告警恢复
-- 162	一般告警		第7路输出控制开关告警
-- 163			告警恢复
-- 164	一般告警		第8路输出控制开关告警
-- 165			告警恢复
-- 166	一般告警		第9路输出控制开关告警
-- 167			告警恢复
-- 168	一般告警		第10路输出控制开关告警
-- 169			告警恢复
-- 170	一般告警		第11路输出控制开关告警
-- 171			告警恢复
-- 172	一般告警		第12路输出控制开关告警
-- 173			告警恢复
-- 174	一般告警		第13路输出控制开关告警
-- 175			告警恢复
-- 176	一般告警		第14路输出控制开关告警
-- 177			告警恢复
-- 178	一般告警		第15路输出控制开关告警
-- 179			告警恢复
-- 180	一般告警		第16路输出控制开关告警
-- 181			告警恢复
-- 182	一般告警		第17路输出控制开关告警
-- 183			告警恢复
-- 184	一般告警		第18路输出控制开关告警
-- 185			告警恢复
-- 186	一般告警		第19路输出控制开关告警
-- 187			告警恢复
-- 188	一般告警		第20路输出控制开关告警
-- 189			告警恢复
-- 			
-- 200	一般告警		第1路外接开关传感器告警
-- 201			告警恢复
-- 202	一般告警		第2路外接开关传感器告警
-- 203			告警恢复
-- 204	一般告警		第3路外接开关传感器告警
-- 205			告警恢复
-- 206	一般告警		第4路外接开关传感器告警
-- 207			告警恢复
-- 
-- 
		-- 1.3.6.1.4.1.2011.2.82.1.101.1.2.9
		hwPduWarningStatus OBJECT-TYPE
			SYNTAX OCTET STRING (SIZE (0..512))
			MAX-ACCESS read-only
			STATUS deprecated
			DESCRIPTION
				"Get warning status of PDU.
				
				16-channel input voltage alarm
				16-channel output switch sensor
				4-channel external switch sensor
				Two device fault
				A board temperature sensor"
			::= { hwPDUM 9 }

		
-- 输入数据:文件名 PDU2
-- 单板名和文件名之间用空格隔开
-- 
		-- 1.3.6.1.4.1.2011.2.82.1.101.1.2.10
		hwPduLoadFile OBJECT-TYPE
			SYNTAX OCTET STRING (SIZE (0..512))
			MAX-ACCESS read-write
			STATUS current
			DESCRIPTION
				"Upgrade program of PDU.
				
				the operation of writing ,the input of parameter is filename of program and the name of PDU.
				for example: IT11PAMU_V100_LOAD.bin PDU2
				Before the upgrade, you must transfer program to /tmp which is in SMM.
				 	
				the operation of reading, when return value is busy, the program is being upgraded. 
				when return value is OK the program to complete the upgrade, "
			::= { hwPDUM 10 }

		
-- 输入：blade20
-- 返回：加载进度，是ASIC码。
		-- 1.3.6.1.4.1.2011.2.82.1.101.1.2.11
		hwPduLoadProc OBJECT-TYPE
			SYNTAX OCTET STRING (SIZE (0..63))
			MAX-ACCESS read-only
			STATUS current
			DESCRIPTION
				"Program progress of the upgrade."
			::= { hwPDUM 11 }

		
		-- 1.3.6.1.4.1.2011.2.82.1.101.1.2.12
		hwPduReset OBJECT-TYPE
			SYNTAX OCTET STRING (SIZE (0..512))
			MAX-ACCESS read-write
			STATUS current
			DESCRIPTION
				"Reset pdu or get pdum status.
				
				the operation of writing ,we will reset PDU, the input of parameter is index of PDU.
				0: PDU0
				1: PDU1
				2: PDU2
				3: PDU3
				 	
				the operation of reading, when return value is RUNNING, the program of pdum.out is running. 
				when return value is ABSENT, the program of pdum.out is stopping,
				
				After reset PDU, You must wait one minute for PDUM initialization is complete.
				
				"
			::= { hwPDUM 12 }

		
-- 设置Trap IP，包括两个OMU的IP地址和为调试接口而添加的Trap IP
-- 可读写，空格区分。IP个数必须为两个或三个。
-- 默认只有两个值，即两个OMU的IP地址，如有第三个值，即为调试的Trap IP
-- 
-- 示例如下:
-- 172.16.128.1 172.17.128.1
-- 172.16.128.1 172.23.131.123
-- 172.16.128.1 172.17.128.1 172.23.131.123
-- 172.16.128.1 172.17.128.1 0
-- 172.16.128.1 0
-- 
-- IP可以设为0，表示不再使用相应IP
-- 如果原来设置了三个IP，下次设置时可以只设两个IP，表示不再使用第三个IP，效果相当于将第三个IP设为0。
-- 
		-- 1.3.6.1.4.1.2011.2.82.1.101.1.2.13
		hwPdumTrapIpAddr OBJECT-TYPE
			SYNTAX OCTET STRING (SIZE (0..512))
			MAX-ACCESS read-only
			STATUS current
			DESCRIPTION
				"The IP address of the machine that will receive SNMP 
				traps from a smmLocation.
				"
			::= { hwPDUM 13 }

		
		-- 1.3.6.1.4.1.2011.2.82.1.101.1.2.102
		hwPduLinkStatusTable OBJECT-TYPE
			SYNTAX SEQUENCE OF HwPduLinkStatusEntry
			MAX-ACCESS not-accessible
			STATUS current
			DESCRIPTION
				"A table containing the list of Serial Link Status."
			::= { hwPDUM 102 }

		
		-- 1.3.6.1.4.1.2011.2.82.1.101.1.2.102.1
		hwPduLinkStatusEntry OBJECT-TYPE
			SYNTAX HwPduLinkStatusEntry
			MAX-ACCESS not-accessible
			STATUS current
			DESCRIPTION
				"Description."
			INDEX { hwPduLinkStatusIndex }
			::= { hwPduLinkStatusTable 1 }

		
		HwPduLinkStatusEntry ::=
			SEQUENCE { 
				hwPduLinkStatusIndex
					Integer32,
				hwPduLinkStatusNode
					OCTET STRING
			 }

		-- 1.3.6.1.4.1.2011.2.82.1.101.1.2.102.1.1
		hwPduLinkStatusIndex OBJECT-TYPE
			SYNTAX Integer32 (1..4)
			MAX-ACCESS read-only
			STATUS current
			DESCRIPTION
				"Description."
			::= { hwPduLinkStatusEntry 1 }

		
		-- 1.3.6.1.4.1.2011.2.82.1.101.1.2.102.1.2
		hwPduLinkStatusNode OBJECT-TYPE
			SYNTAX OCTET STRING (SIZE (0..512))
			MAX-ACCESS read-only
			STATUS current
			DESCRIPTION
				"Description."
			::= { hwPduLinkStatusEntry 2 }

		
		-- 1.3.6.1.4.1.2011.2.82.1.101.1.2.103
		hwPduVersionTable OBJECT-TYPE
			SYNTAX SEQUENCE OF HwPduVersionEntry
			MAX-ACCESS not-accessible
			STATUS current
			DESCRIPTION
				"A table containing the list of PDU Version."
			::= { hwPDUM 103 }

		
		-- 1.3.6.1.4.1.2011.2.82.1.101.1.2.103.1
		hwPduVersionEntry OBJECT-TYPE
			SYNTAX HwPduVersionEntry
			MAX-ACCESS not-accessible
			STATUS current
			DESCRIPTION
				"Description."
			INDEX { hwPduVersionIndex }
			::= { hwPduVersionTable 1 }

		
		HwPduVersionEntry ::=
			SEQUENCE { 
				hwPduVersionIndex
					Integer32,
				hwPduVersioNode
					OCTET STRING
			 }

		-- 1.3.6.1.4.1.2011.2.82.1.101.1.2.103.1.1
		hwPduVersionIndex OBJECT-TYPE
			SYNTAX Integer32 (1..4)
			MAX-ACCESS read-only
			STATUS current
			DESCRIPTION
				"Description."
			::= { hwPduVersionEntry 1 }

		
		-- 1.3.6.1.4.1.2011.2.82.1.101.1.2.103.1.2
		hwPduVersioNode OBJECT-TYPE
			SYNTAX OCTET STRING (SIZE (0..512))
			MAX-ACCESS read-only
			STATUS current
			DESCRIPTION
				"Description."
			::= { hwPduVersionEntry 2 }

		
		-- 1.3.6.1.4.1.2011.2.82.1.101.1.2.104
		hwPduConfigDataTable OBJECT-TYPE
			SYNTAX SEQUENCE OF HwPduConfigDataEntry
			MAX-ACCESS not-accessible
			STATUS current
			DESCRIPTION
				"A table containing the list of config data."
			::= { hwPDUM 104 }

		
		-- 1.3.6.1.4.1.2011.2.82.1.101.1.2.104.1
		hwPduConfigDataEntry OBJECT-TYPE
			SYNTAX HwPduConfigDataEntry
			MAX-ACCESS not-accessible
			STATUS current
			DESCRIPTION
				"Description."
			INDEX { hwPduConfigDataIndex }
			::= { hwPduConfigDataTable 1 }

		
		HwPduConfigDataEntry ::=
			SEQUENCE { 
				hwPduConfigDataIndex
					Integer32,
				hwPduConfigDataNode
					OCTET STRING
			 }

		-- 1.3.6.1.4.1.2011.2.82.1.101.1.2.104.1.1
		hwPduConfigDataIndex OBJECT-TYPE
			SYNTAX Integer32 (1..4)
			MAX-ACCESS read-only
			STATUS current
			DESCRIPTION
				"Description."
			::= { hwPduConfigDataEntry 1 }

		
		-- 1.3.6.1.4.1.2011.2.82.1.101.1.2.104.1.2
		hwPduConfigDataNode OBJECT-TYPE
			SYNTAX OCTET STRING (SIZE (0..512))
			MAX-ACCESS read-write
			STATUS current
			DESCRIPTION
				"Description."
			::= { hwPduConfigDataEntry 2 }

		
		-- 1.3.6.1.4.1.2011.2.82.1.101.1.2.105
		hwPduWarningMaskTable OBJECT-TYPE
			SYNTAX SEQUENCE OF HwPduWarningMaskEntry
			MAX-ACCESS not-accessible
			STATUS current
			DESCRIPTION
				"A table containing the list of alarm enable."
			::= { hwPDUM 105 }

		
		-- 1.3.6.1.4.1.2011.2.82.1.101.1.2.105.1
		hwPduWarningMaskEntry OBJECT-TYPE
			SYNTAX HwPduWarningMaskEntry
			MAX-ACCESS not-accessible
			STATUS current
			DESCRIPTION
				"Description."
			INDEX { hwPduWarningMaskIndex }
			::= { hwPduWarningMaskTable 1 }

		
		HwPduWarningMaskEntry ::=
			SEQUENCE { 
				hwPduWarningMaskIndex
					Integer32,
				hwPduWarningMaskNode
					OCTET STRING
			 }

		-- 1.3.6.1.4.1.2011.2.82.1.101.1.2.105.1.1
		hwPduWarningMaskIndex OBJECT-TYPE
			SYNTAX Integer32 (1..4)
			MAX-ACCESS read-only
			STATUS current
			DESCRIPTION
				"Description."
			::= { hwPduWarningMaskEntry 1 }

		
		-- 1.3.6.1.4.1.2011.2.82.1.101.1.2.105.1.2
		hwPduWarningMaskNode OBJECT-TYPE
			SYNTAX OCTET STRING (SIZE (0..512))
			MAX-ACCESS read-write
			STATUS current
			DESCRIPTION
				"Description."
			::= { hwPduWarningMaskEntry 2 }

		
		-- 1.3.6.1.4.1.2011.2.82.1.101.1.2.106
		hwPduAnalogTable OBJECT-TYPE
			SYNTAX SEQUENCE OF HwPduAnalogEntry
			MAX-ACCESS not-accessible
			STATUS current
			DESCRIPTION
				"A table containing the list of PDU analog value."
			::= { hwPDUM 106 }

		
		-- 1.3.6.1.4.1.2011.2.82.1.101.1.2.106.1
		hwPduAnalogEntry OBJECT-TYPE
			SYNTAX HwPduAnalogEntry
			MAX-ACCESS not-accessible
			STATUS current
			DESCRIPTION
				"Description."
			INDEX { hwPduAnalogIndex }
			::= { hwPduAnalogTable 1 }

		
		HwPduAnalogEntry ::=
			SEQUENCE { 
				hwPduAnalogIndex
					Integer32,
				hwPduAnalogNode
					OCTET STRING
			 }

		-- 1.3.6.1.4.1.2011.2.82.1.101.1.2.106.1.1
		hwPduAnalogIndex OBJECT-TYPE
			SYNTAX Integer32 (1..4)
			MAX-ACCESS read-only
			STATUS current
			DESCRIPTION
				"Description."
			::= { hwPduAnalogEntry 1 }

		
		-- 1.3.6.1.4.1.2011.2.82.1.101.1.2.106.1.2
		hwPduAnalogNode OBJECT-TYPE
			SYNTAX OCTET STRING (SIZE (0..512))
			MAX-ACCESS read-only
			STATUS current
			DESCRIPTION
				"Description."
			::= { hwPduAnalogEntry 2 }

		
		-- 1.3.6.1.4.1.2011.2.82.1.101.1.2.107
		hwBuzzerSwTable OBJECT-TYPE
			SYNTAX SEQUENCE OF HwBuzzerSwEntry
			MAX-ACCESS not-accessible
			STATUS current
			DESCRIPTION
				"A table containing the list of buzzer switch."
			::= { hwPDUM 107 }

		
		-- 1.3.6.1.4.1.2011.2.82.1.101.1.2.107.1
		hwBuzzerSwEntry OBJECT-TYPE
			SYNTAX HwBuzzerSwEntry
			MAX-ACCESS not-accessible
			STATUS current
			DESCRIPTION
				"Description."
			INDEX { hwBuzzerSwIndex }
			::= { hwBuzzerSwTable 1 }

		
		HwBuzzerSwEntry ::=
			SEQUENCE { 
				hwBuzzerSwIndex
					Integer32,
				hwBuzzerSwNode
					OCTET STRING
			 }

		-- 1.3.6.1.4.1.2011.2.82.1.101.1.2.107.1.1
		hwBuzzerSwIndex OBJECT-TYPE
			SYNTAX Integer32 (1..4)
			MAX-ACCESS read-only
			STATUS current
			DESCRIPTION
				"Description."
			::= { hwBuzzerSwEntry 1 }

		
		-- 1.3.6.1.4.1.2011.2.82.1.101.1.2.107.1.2
		hwBuzzerSwNode OBJECT-TYPE
			SYNTAX OCTET STRING
			MAX-ACCESS read-write
			STATUS current
			DESCRIPTION
				"Description."
			::= { hwBuzzerSwEntry 2 }

		
		-- 1.3.6.1.4.1.2011.2.82.1.101.1.2.108
		hwPduResetReasonTable OBJECT-TYPE
			SYNTAX SEQUENCE OF HwPduResetReasonEntry
			MAX-ACCESS not-accessible
			STATUS current
			DESCRIPTION
				"A table containing the list of pdu reset reason."
			::= { hwPDUM 108 }

		
		-- 1.3.6.1.4.1.2011.2.82.1.101.1.2.108.1
		hwPduResetReasonEntry OBJECT-TYPE
			SYNTAX HwPduResetReasonEntry
			MAX-ACCESS not-accessible
			STATUS current
			DESCRIPTION
				"Description."
			INDEX { hwPduResetReasoIndex }
			::= { hwPduResetReasonTable 1 }

		
		HwPduResetReasonEntry ::=
			SEQUENCE { 
				hwPduResetReasoIndex
					Integer32,
				hwPduResetReasonNode
					OCTET STRING
			 }

		-- 1.3.6.1.4.1.2011.2.82.1.101.1.2.108.1.1
		hwPduResetReasoIndex OBJECT-TYPE
			SYNTAX Integer32 (1..4)
			MAX-ACCESS read-only
			STATUS current
			DESCRIPTION
				"Description."
			::= { hwPduResetReasonEntry 1 }

		
		-- 1.3.6.1.4.1.2011.2.82.1.101.1.2.108.1.2
		hwPduResetReasonNode OBJECT-TYPE
			SYNTAX OCTET STRING (SIZE (0..512))
			MAX-ACCESS read-only
			STATUS current
			DESCRIPTION
				"Description."
			::= { hwPduResetReasonEntry 2 }

		
		-- 1.3.6.1.4.1.2011.2.82.1.101.1.2.109
		hwPduWarningStatusTable OBJECT-TYPE
			SYNTAX SEQUENCE OF HwPduWarningStatusEntry
			MAX-ACCESS not-accessible
			STATUS current
			DESCRIPTION
				"A table containing the list of warning status."
			::= { hwPDUM 109 }

		
		-- 1.3.6.1.4.1.2011.2.82.1.101.1.2.109.1
		hwPduWarningStatusEntry OBJECT-TYPE
			SYNTAX HwPduWarningStatusEntry
			MAX-ACCESS not-accessible
			STATUS current
			DESCRIPTION
				"Description."
			INDEX { hwPduWarningStatusIndex }
			::= { hwPduWarningStatusTable 1 }

		
		HwPduWarningStatusEntry ::=
			SEQUENCE { 
				hwPduWarningStatusIndex
					Integer32,
				hwPduWarningStatusNode
					OCTET STRING
			 }

		-- 1.3.6.1.4.1.2011.2.82.1.101.1.2.109.1.1
		hwPduWarningStatusIndex OBJECT-TYPE
			SYNTAX Integer32 (1..4)
			MAX-ACCESS read-only
			STATUS current
			DESCRIPTION
				"Description."
			::= { hwPduWarningStatusEntry 1 }

		
		-- 1.3.6.1.4.1.2011.2.82.1.101.1.2.109.1.2
		hwPduWarningStatusNode OBJECT-TYPE
			SYNTAX OCTET STRING (SIZE (0..512))
			MAX-ACCESS read-only
			STATUS current
			DESCRIPTION
				"Description."
			::= { hwPduWarningStatusEntry 2 }

		
		-- 1.3.6.1.4.1.2011.2.82.1.101.1.2.111
		hwPduEidTable OBJECT-TYPE
			SYNTAX SEQUENCE OF HwPduEidEntry
			MAX-ACCESS not-accessible
			STATUS current
			DESCRIPTION
				"A table containing the list of electronic label."
			::= { hwPDUM 111 }

		
		-- 1.3.6.1.4.1.2011.2.82.1.101.1.2.111.1
		hwPduEidEntry OBJECT-TYPE
			SYNTAX HwPduEidEntry
			MAX-ACCESS not-accessible
			STATUS current
			DESCRIPTION
				"Description."
			INDEX { hwPduEidIndex }
			::= { hwPduEidTable 1 }

		
		HwPduEidEntry ::=
			SEQUENCE { 
				hwPduEidIndex
					Integer32,
				hwPduEidNode
					OCTET STRING,
				hwPduE2pEidNode
					OCTET STRING,
				hwPduLogNode
					OCTET STRING
			 }

		-- 1.3.6.1.4.1.2011.2.82.1.101.1.2.111.1.1
		hwPduEidIndex OBJECT-TYPE
			SYNTAX Integer32 (1..4)
			MAX-ACCESS read-only
			STATUS current
			DESCRIPTION
				"Description."
			::= { hwPduEidEntry 1 }

		
		-- 1.3.6.1.4.1.2011.2.82.1.101.1.2.111.1.2
		hwPduEidNode OBJECT-TYPE
			SYNTAX OCTET STRING (SIZE (0..2048))
			MAX-ACCESS read-only
			STATUS current
			DESCRIPTION
				"Description."
			::= { hwPduEidEntry 2 }

		
		-- 1.3.6.1.4.1.2011.2.82.1.101.1.2.111.1.3
		hwPduE2pEidNode OBJECT-TYPE
			SYNTAX OCTET STRING (SIZE (0..2048))
			MAX-ACCESS read-only
			STATUS current
			DESCRIPTION
				"Description."
			::= { hwPduEidEntry 3 }

		
		-- 1.3.6.1.4.1.2011.2.82.1.101.1.2.111.1.4
		hwPduLogNode OBJECT-TYPE
			SYNTAX OCTET STRING (SIZE (0..2048))
			MAX-ACCESS read-only
			STATUS current
			DESCRIPTION
				"Description."
			::= { hwPduEidEntry 4 }

		
		-- 1.3.6.1.4.1.2011.2.82.1.101.1.2.112
		hwPduAlmsTable OBJECT-TYPE
			SYNTAX SEQUENCE OF HwPduAlmsEntry
			MAX-ACCESS not-accessible
			STATUS current
			DESCRIPTION
				"A table containing the list of warning which not include the status is ok."
			::= { hwPDUM 112 }

		
		-- 1.3.6.1.4.1.2011.2.82.1.101.1.2.112.1
		hwPduAlmsEntry OBJECT-TYPE
			SYNTAX HwPduAlmsEntry
			MAX-ACCESS not-accessible
			STATUS current
			DESCRIPTION
				"Description."
			INDEX { hwPduAnalogIndex }
			::= { hwPduAlmsTable 1 }

		
		HwPduAlmsEntry ::=
			SEQUENCE { 
				hwPduAlmsIndex
					Integer32,
				hwPduAlmsNode
					OCTET STRING
			 }

		-- 1.3.6.1.4.1.2011.2.82.1.101.1.2.112.1.1
		hwPduAlmsIndex OBJECT-TYPE
			SYNTAX Integer32 (1..4)
			MAX-ACCESS read-only
			STATUS current
			DESCRIPTION
				"Description."
			::= { hwPduAlmsEntry 1 }

		
		-- 1.3.6.1.4.1.2011.2.82.1.101.1.2.112.1.2
		hwPduAlmsNode OBJECT-TYPE
			SYNTAX OCTET STRING (SIZE (0..512))
			MAX-ACCESS read-only
			STATUS current
			DESCRIPTION
				"Description."
			::= { hwPduAlmsEntry 2 }

		
		-- 1.3.6.1.4.1.2011.2.82.1.101.1.2.113
		hwPduTimeTable OBJECT-TYPE
			SYNTAX SEQUENCE OF HwPduTimeEntry
			MAX-ACCESS not-accessible
			STATUS current
			DESCRIPTION
				"A table containing the list of warning which not include the status is ok."
			::= { hwPDUM 113 }

		
		-- 1.3.6.1.4.1.2011.2.82.1.101.1.2.113.1
		hwPduTimeEntry OBJECT-TYPE
			SYNTAX HwPduTimeEntry
			MAX-ACCESS not-accessible
			STATUS current
			DESCRIPTION
				"Description."
			INDEX { hwPduAnalogIndex }
			::= { hwPduTimeTable 1 }

		
		HwPduTimeEntry ::=
			SEQUENCE { 
				hwPduTimeIndex
					Integer32,
				hwPduTimeNode
					OCTET STRING
			 }

		-- 1.3.6.1.4.1.2011.2.82.1.101.1.2.113.1.1
		hwPduTimeIndex OBJECT-TYPE
			SYNTAX Integer32 (1..4)
			MAX-ACCESS read-only
			STATUS current
			DESCRIPTION
				"Description."
			::= { hwPduTimeEntry 1 }

		
		-- 1.3.6.1.4.1.2011.2.82.1.101.1.2.113.1.2
		hwPduTimeNode OBJECT-TYPE
			SYNTAX OCTET STRING (SIZE (0..512))
			MAX-ACCESS read-only
			STATUS current
			DESCRIPTION
				"Description."
			::= { hwPduTimeEntry 2 }

		
	
	END

--
-- HW_SMM_PDUM.mib
--
