--
-- OSCA-MIB.my
-- MIB generated by MG-SOFT Visual MIB Builder Version 3.0 Build 253
-- Wednesday, November 14, 2012 at 10:00:36
-- 

	HWSMM-MIB DEFINITIONS ::= BEGIN
 
		IMPORTS
			DisplayString			
				FROM RFC1213-MIB			
			enterprises, IpAddress, OBJECT-TYPE, MODULE-IDENTITY			
				FROM SNMPv2-SMI;
	
	
		hwSMM MODULE-IDENTITY 
			LAST-UPDATED "201407070000Z"		 
			ORGANIZATION 
				"CGA BASE PDT"
			CONTACT-INFO 
				" Huawei Co.  "
			DESCRIPTION 
				"The MIB module for stub module SMM."
			::= { hwUSP 82 }
		
	
	
--
-- Node definitions
--
	
--  
		-- 1.3.6.1.4.1.2011
		huawei OBJECT IDENTIFIER ::= { enterprises 2011 }
		
		-- 1.3.6.1.4.1.2011.2
		products OBJECT IDENTIFIER ::= { huawei 2 }
		
		-- 1.3.6.1.4.1.2011.2.82
		hwOSTA OBJECT IDENTIFIER ::= { products 82 }
		
		-- 1.3.6.1.4.1.2011.2.82.1
		hwUSP OBJECT IDENTIFIER ::= { hwOSTA 1 }
		
 		system OBJECT IDENTIFIER ::= { hwSMM 1 }
		
 		systemHealth OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"systemHealth information about a particular systemLocation. 
				This will be one of the following:
				(0-ok, 1-minor, 2-major, 3-majorandminor,4-critical,5-criticalandminor,6-criticalandmajor,7-criticalandmajorandminor)"
			::= { system 1 }
		
 		systemUnHealthyLocations OBJECT-TYPE
			SYNTAX DisplayString
			MAX-ACCESS read-only
			STATUS current
			DESCRIPTION
				"Used with the systemLocation to find out what Locations 
				are having problems."
			::= { system 2 }
		
 		shelf OBJECT IDENTIFIER ::= { hwSMM 2 }
		
 		shelfListTargets OBJECT-TYPE
			SYNTAX DisplayString
			MAX-ACCESS read-only
			STATUS current
			DESCRIPTION
				"Used to find out what targets are available on a shelfLocation. 
				E.g. Getting the list of sensors in the shelf."
			::= { shelf 1 }
		
		shelfDomain OBJECT-TYPE
			SYNTAX DisplayString
			MAX-ACCESS read-write
			STATUS current
			DESCRIPTION
				"Set and query the shelf domain info."
			::= { shelf 2 }
		
 		shelfLocation OBJECT-TYPE
			SYNTAX DisplayString
			MAX-ACCESS read-write
			STATUS current
			DESCRIPTION
				"A shelfLocation information."
			::= { shelf 4 }
		
 		shelfHealth OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"Health information about a particular Location. 
				This will be one of the following:
				(0-ok, 1-minor, 2-major, 3-majorandminor,4-critical,5-criticalandminor,6-criticalandmajor,7-criticalandmajorandminor)"
			::= { shelf 5 }
		
 		shelfHealthEvents OBJECT-TYPE
			SYNTAX DisplayString
			MAX-ACCESS read-only
			STATUS current
			DESCRIPTION
				"Events that contribute to the Health of the Location.  
				This is a list of events currently happening on the 
				Location."
			::= { shelf 6 }
		
 		shelfChassisID OBJECT-TYPE
			SYNTAX DisplayString
			MAX-ACCESS read-write
			STATUS current
			DESCRIPTION
				"A ChassisID information."
			::= { shelf 8 }
		
 		shelfFanTraycontrolmode OBJECT-TYPE
			SYNTAX INTEGER
				{
				auto(0),
				manual(1)
				}
			MAX-ACCESS read-write
			STATUS current
			DESCRIPTION
				"Get the mode of fantray."
			::= { shelf 10 }

		
 		shelfRealTimePower OBJECT-TYPE
			SYNTAX INTEGER
			MAX-ACCESS read-only
			STATUS current
			DESCRIPTION
				"Get the realtime power of shelf."
			::= { shelf 13 }
		
 		shelfPowerCappingEnable OBJECT-TYPE
			SYNTAX INTEGER
				{
				disable(0),
				enable(1)
				}
			MAX-ACCESS read-write
			STATUS current
			DESCRIPTION
				"Get the Power Capping Type of shelf."
			::= { shelf 14 }
		
 		shelfPowerCapping OBJECT-TYPE
			SYNTAX DisplayString
			MAX-ACCESS read-write
			STATUS current
			DESCRIPTION
				"Get the Power Capping value of shelf."
			::= { shelf 15 }
		
 		shelfSubnet OBJECT-TYPE
			SYNTAX DisplayString
			MAX-ACCESS read-write
			STATUS current
			DESCRIPTION
				"Get or Set Subnet."
			::= { shelf 17 }
		
 		shelfChassisName OBJECT-TYPE
			SYNTAX DisplayString
			MAX-ACCESS read-write
			STATUS current
			DESCRIPTION
				"Get or Set shelfChassisName"
			::= { shelf 18 }
		
 		shelfPsuSleepConfig OBJECT-TYPE
			SYNTAX DisplayString
			MAX-ACCESS read-write
			STATUS current
			DESCRIPTION
				"Get or Set shelfPsuSleepConfig"
			::= { shelf 21 }
		
 		shelfPsuSleepStatus OBJECT-TYPE
			SYNTAX DisplayString
			MAX-ACCESS read-only
			STATUS current
			DESCRIPTION
				"Get shelfPsuSleepStatus"
			::= { shelf 22 }
		
		shelfRmvAlarmState OBJECT-TYPE
			SYNTAX DisplayString
			MAX-ACCESS read-write
			STATUS current
			DESCRIPTION
				"Get and Set remove alarm state"
			::= { shelf 23 }
 		shelfFruDescriptionTable OBJECT-TYPE
			SYNTAX SEQUENCE OF ShelfFruDescriptionEntry
			MAX-ACCESS not-accessible
			STATUS current
			DESCRIPTION
				"A table containing the list of Fru information."
			::= { shelf 2001 }
		
 		shelfFruDescriptionEntry OBJECT-TYPE
			SYNTAX ShelfFruDescriptionEntry
			MAX-ACCESS not-accessible
			STATUS current
			DESCRIPTION
				"Information about a particular current sensor."
			INDEX { shelfNumber }
			::= { shelfFruDescriptionTable 1 }
		
		ShelfFruDescriptionEntry ::=
			SEQUENCE { 
				shelfNumber
					INTEGER,
				shelfPartNumber
					DisplayString,
				shelfSerialNumber
					DisplayString,
				shelfType
					DisplayString,
				shelffruAll
					DisplayString
			 }

 		shelfNumber OBJECT-TYPE
			SYNTAX INTEGER
			MAX-ACCESS not-accessible
			STATUS current
			DESCRIPTION
				" "
			::= { shelfFruDescriptionEntry 1 }
		
 		shelfPartNumber OBJECT-TYPE
			SYNTAX DisplayString
			MAX-ACCESS read-only
			STATUS current
			DESCRIPTION
				"Used to read the shelf Part Number from the Fru."
			::= { shelfFruDescriptionEntry 14 }
		
 		shelfSerialNumber OBJECT-TYPE
			SYNTAX DisplayString
			MAX-ACCESS read-write
			STATUS current
			DESCRIPTION
				"Used to read the shelf Serial Number from the Fru."
			::= { shelfFruDescriptionEntry 15 }
		
 		shelfType OBJECT-TYPE
			SYNTAX DisplayString
			MAX-ACCESS read-only
			STATUS current
			DESCRIPTION
				"Used to read the shelf Type from the Fru."
			::= { shelfFruDescriptionEntry 16 }
		
 		shelffruAll OBJECT-TYPE
			SYNTAX DisplayString
			MAX-ACCESS read-only
			STATUS current
			DESCRIPTION
				"Used to read the shelf fru info all "
			::= { shelfFruDescriptionEntry 17 }
		
 		smm OBJECT IDENTIFIER ::= { hwSMM 3 }
		
 		softwareVersion OBJECT-TYPE
			SYNTAX DisplayString
			MAX-ACCESS read-only
			STATUS current
			DESCRIPTION
				"The version of the smm software."
			::= { smm 1 }
		
 		smmRedundancy OBJECT-TYPE
			SYNTAX DisplayString
			MAX-ACCESS read-only
			STATUS current
			DESCRIPTION
				"smm redundancy information."
			::= { smm 2 }
		
 		smmPICMGProperties OBJECT-TYPE
			SYNTAX DisplayString
			MAX-ACCESS read-only
			STATUS current
			DESCRIPTION
				"display the version of the PICMG"
			::= { smm 6 }
		
 		smmDeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { smm 7 }
		
 		smmPresence OBJECT-TYPE
			SYNTAX INTEGER
				{
				not-present(0),
				present(1),
				indeterminate(2)
				}
			MAX-ACCESS read-only
			STATUS current
			DESCRIPTION
				"Used to find out if a smmLocation is present in the shelf.
				0 - not present
				1 - present
				2 - indeterminate"
			::= { smm 8 }
		
 		smmHealth OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"smmHealth information about a particular smmLocation. 
				This will be one of the following:
				(0-ok, 1-minor, 2-major, 3-majorandminor,4-critical,5-criticalandminor,6-criticalandmajor,7-criticalandmajorandminor)"
			::= { smm 9 }
		
 		smmHealthEvents OBJECT-TYPE
			SYNTAX DisplayString
			MAX-ACCESS read-only
			STATUS current
			DESCRIPTION
				"Events that contribute to the smmHealth of the smmLocation.  
				This is a list of events currently happening on the 
				smmLocation."
			::= { smm 10 }
		
 		smmSNMPTrapEnable OBJECT-TYPE
			SYNTAX INTEGER
				{
				disable(0),
				enable(1)
				}
			MAX-ACCESS read-write
			STATUS current
			DESCRIPTION
				"Used to set or query SNMP trap enabled status.
				0 - disable
				1 - enable"
			::= { smm 11 }
		
 		smmFailover OBJECT-TYPE
			SYNTAX INTEGER { enable(1) }
			MAX-ACCESS read-write
			STATUS current
			DESCRIPTION
				"Used to induce a failover from the active smm to the standby smm.
				1 - enable"
			::= { smm 12 }
	

		smmListPresent OBJECT-TYPE
			SYNTAX DisplayString
			MAX-ACCESS read-only
			STATUS current
			DESCRIPTION
				"list of present Entities information."
			::= { smm 18 }
		
 		smmClearSEL OBJECT-TYPE
			SYNTAX INTEGER { clear(1) }
			MAX-ACCESS read-write
			STATUS current
			DESCRIPTION
				"To clear the SEL set the object with 
				1 - clear.  Other value - has no effect"
			::= { smm 20 }
		
 		smmSynchronize OBJECT-TYPE
			SYNTAX INTEGER
				{
				not-set(0),
				set(1)
				}
			MAX-ACCESS read-write
			STATUS current
			DESCRIPTION
				"make the active and the stangby SMM synchronize.  Valid value: 1,0"
			::= { smm 24 }
		
 		smmSNMPTrapAddress1 OBJECT-TYPE
			SYNTAX IpAddress
			MAX-ACCESS read-write
			STATUS current
			DESCRIPTION
				"The IP address of the machine that will receive SNMP 
				traps from a smmLocation."
			::= { smm 27 }
		
 		smmSNMPTrapAddress2 OBJECT-TYPE
			SYNTAX IpAddress
			MAX-ACCESS read-write
			STATUS current
			DESCRIPTION
				"The IP address of the machine that will receive SNMP 
				traps from a smmLocation."
			::= { smm 28 }
		
 		smmSNMPTrapAddress3 OBJECT-TYPE
			SYNTAX IpAddress
			MAX-ACCESS read-write
			STATUS current
			DESCRIPTION
				"The IP address of the machine that will receive SNMP 
				traps from a smmLocation."
			::= { smm 29 }
		
 		smmSNMPTrapAddress4 OBJECT-TYPE
			SYNTAX IpAddress
			MAX-ACCESS read-write
			STATUS current
			DESCRIPTION
				"The IP address of the machine that will receive SNMP 
				traps from a smmLocation."
			::= { smm 30 }
		
 		smmSNMPTrapAddress5 OBJECT-TYPE
			SYNTAX IpAddress
			MAX-ACCESS read-write
			STATUS current
			DESCRIPTION
				"The IP address of the machine that will receive SNMP 
				traps from a smmLocation."
			::= { smm 31 }
		
 		smmSNMPTrapCommunity OBJECT-TYPE
			SYNTAX DisplayString
			MAX-ACCESS read-write
			STATUS current
			DESCRIPTION
				"SNMP community name."
			::= { smm 32 }
		
 		smmSNMPTrapVersion OBJECT-TYPE
			SYNTAX DisplayString
			MAX-ACCESS read-write
			STATUS current
			DESCRIPTION
				"SNMP trap version."
			::= { smm 33 }
		
 		smmSNMPTrapPort OBJECT-TYPE
			SYNTAX DisplayString
			MAX-ACCESS read-write
			STATUS current
			DESCRIPTION
				"SNMP trap port."
			::= { smm 34 }
		
 		smmKVMConnect OBJECT-TYPE
			SYNTAX DisplayString
			MAX-ACCESS read-only
			STATUS current
			DESCRIPTION
				"get of new kvm connect information.return: <key>,<port>"
			::= { smm 40 }
		
 		smmSnmpReboot OBJECT-TYPE
			SYNTAX INTEGER { reboot(0) }
			MAX-ACCESS read-write
			STATUS current
			DESCRIPTION
				"Reboot the SMM"
			::= { smm 41 }
		
 		smmUniteLoad OBJECT-TYPE
			SYNTAX DisplayString
			MAX-ACCESS read-write
			STATUS current
			DESCRIPTION
				"load firmware file for blades.
				set value:firmware;bladename(eg:hcsa.fw,CN2XCBA04301.fw;blade1,blade7)				
				firmwaretype:BMC FPGA BIOS
				bladename:blade1~14,fantray1~2,pem1~2
				"
			::= { smm 43 }
		
 		smmUniteLoadProgress OBJECT-TYPE
			SYNTAX DisplayString
			MAX-ACCESS read-only
			STATUS current
			DESCRIPTION
				"get load progress of blade.				
				result value:progress(eg:blade1:80% blade2:82% fantray1:81%)
				"
			::= { smm 44 }
		
 		smmPduEnable OBJECT-TYPE
			SYNTAX INTEGER
				{
				disabled(0),
				enabled(1)
				}
			MAX-ACCESS read-write
			STATUS current
			DESCRIPTION
				" Enabled and disabled the soft chassis id."
			::= { smm 47 }
		
 		smmIpMode OBJECT-TYPE
			SYNTAX INTEGER
				{
				static(1),
				dhcp(2)
				}
			MAX-ACCESS read-write
			STATUS current
			DESCRIPTION
				" Get or set the IP mode."
			::= { smm 48 }
		
 		smmHostname OBJECT-TYPE
			SYNTAX DisplayString
			MAX-ACCESS read-write
			STATUS current
			DESCRIPTION
				" Get or set the Hostname."
			::= { smm 49 }
		
 		smmOutPortMode OBJECT-TYPE
			SYNTAX INTEGER
			MAX-ACCESS read-write
			STATUS current
			DESCRIPTION
				" Get or set the OutPortMode."
			::= { smm 50 }
		
 		smmSmalert OBJECT-TYPE
			SYNTAX INTEGER
			MAX-ACCESS read-write
			STATUS current
			DESCRIPTION
				" Get or set the Smalert."
			::= { smm 51 }
		
 		smmUseradd OBJECT-TYPE
			SYNTAX DisplayString
			MAX-ACCESS read-write
			STATUS current
			DESCRIPTION
				"add user"
			::= { smm 52 }
		
 		smmUserdel OBJECT-TYPE
			SYNTAX DisplayString
			MAX-ACCESS read-write
			STATUS current
			DESCRIPTION
				"delete user"
			::= { smm 53 }
		
 		smmUserpasswd OBJECT-TYPE
			SYNTAX DisplayString
			MAX-ACCESS read-write
			STATUS current
			DESCRIPTION
				"change password"
			::= { smm 54 }
		
 		smmUserpropertychg OBJECT-TYPE
			SYNTAX DisplayString
			MAX-ACCESS read-write
			STATUS current
			DESCRIPTION
				"change user propertychg"
			::= { smm 55 }
		
 		smmUserpasswdcomplex OBJECT-TYPE
			SYNTAX OCTET STRING
			MAX-ACCESS read-write
			STATUS current
			DESCRIPTION
				"change passwdcomplex"
			::= { smm 56 }
		
		smmPoweronControl OBJECT-TYPE
			SYNTAX DisplayString
			MAX-ACCESS read-write
			STATUS current
			DESCRIPTION
				"poweron control configure"
			::= { smm 57 }
		
		smmAuthKey OBJECT-TYPE
			SYNTAX DisplayString
			MAX-ACCESS read-write
			STATUS current
			DESCRIPTION
				"key configure"
			::= { smm 58 }
			
		smmPoweronResp OBJECT-TYPE
			SYNTAX DisplayString
			MAX-ACCESS read-write
			STATUS current
			DESCRIPTION
				"poweron control response"
			::= { smm 59 }
				
		smmSecretKVMConnect OBJECT-TYPE
			SYNTAX DisplayString
			MAX-ACCESS read-only
			STATUS current
			DESCRIPTION
				"get of secret kvm connect information.return: <key>,<port>"
			::= { smm 60 }

		smmUserIntfAuth OBJECT-TYPE
			SYNTAX DisplayString
			MAX-ACCESS read-write
			STATUS current
			DESCRIPTION
				"user interface access authority"
			::= { smm 61 }
			
 		smmGateway OBJECT-TYPE
			SYNTAX DisplayString
			MAX-ACCESS read-write
			STATUS current
			DESCRIPTION
				"Read or set the gateway."
			::= { smm 64 }
		
 		smmNTPEnable OBJECT-TYPE
			SYNTAX INTEGER
			MAX-ACCESS read-write
			STATUS current
			DESCRIPTION
				"Get or set the NTP status.
				settable format:
				1(enable);
				0(disable)"
			::= { smm 65 }
		
 		smmNTPServerip OBJECT-TYPE
			SYNTAX DisplayString
			MAX-ACCESS read-write
			STATUS current
			DESCRIPTION
				"Get or set the NTP server-ip.
				settable format:
				prefer-server-ip,server-ip
				for example:172.172.1.0,172.172.1.0"
			::= { smm 66 }
		
 		smmNTPSyncinterval OBJECT-TYPE
			SYNTAX DisplayString
			MAX-ACCESS read-write
			STATUS current
			DESCRIPTION
				"Get or set the NTP synchronized interval.
				settable format:
				minsyncinterval,maxsyncinterval
				for example:6,8"
			::= { smm 67 }
		
 		smmTimeZone OBJECT-TYPE
			SYNTAX DisplayString
			MAX-ACCESS read-write
			STATUS current
			DESCRIPTION
				"Get or set the timezone.
				settable format:
				timezone
				for example:GMT+8"
			::= { smm 68 }
		
 		smmLCDUIDled OBJECT-TYPE
			SYNTAX DisplayString
			MAX-ACCESS read-write
			STATUS current
			DESCRIPTION
				"Read or set the UIDled"
			::= { smm 69 }
		
 		smmPowerOnInterval OBJECT-TYPE
			SYNTAX INTEGER
			MAX-ACCESS read-write
			STATUS current
			DESCRIPTION
				"Get or Set smmPowerOnInterval"
			::= { smm 70 }
		
 		smmOtherVersion OBJECT-TYPE
			SYNTAX DisplayString
			MAX-ACCESS read-only
			STATUS current
			DESCRIPTION
				"The version of the smm software."
			::= { smm 71 }
		
	
		smmDomainCreate OBJECT-TYPE
			SYNTAX DisplayString
			MAX-ACCESS read-create
			STATUS current
			DESCRIPTION
				"Create a new smmDomain."
			::= { smm 72 }
	
		smmDomainDel OBJECT-TYPE
			SYNTAX DisplayString
			MAX-ACCESS read-create
			STATUS current
			DESCRIPTION
				"Delete SMM Domain with domain name."
			::= { smm 73 }
		
		smmProductName OBJECT-TYPE
			SYNTAX DisplayString
			MAX-ACCESS read-only
			STATUS current
			DESCRIPTION
				"The version of the smm software."
			::= { smm 74 }

		
		smmDNSHostname OBJECT-TYPE
			SYNTAX DisplayString
			MAX-ACCESS read-write
			STATUS current
			DESCRIPTION
				"Get or set the DNS hostname."
			::= { smm 75 }

		
		smmDNSDomainname OBJECT-TYPE
			SYNTAX DisplayString
			MAX-ACCESS read-write
			STATUS current
			DESCRIPTION
				"Get or set the DNS domainname."
			::= { smm 76 }

		
		smmDNSServerip OBJECT-TYPE
			SYNTAX DisplayString
			MAX-ACCESS read-write
			STATUS current
			DESCRIPTION
				"Get or set the DNS server-ip.
				settable format:
				maindnsserverip,bakdnsserverip
				for example:172.172.1.0,172.172.2.0"
			::= { smm 77 }

		
		smmBundleVersion OBJECT-TYPE
			SYNTAX DisplayString
			MAX-ACCESS read-write
			STATUS current
			DESCRIPTION
				"Get or set the smm bundle version."
			::= { smm 78 }

		
		smmOtherReboot OBJECT-TYPE
			SYNTAX INTEGER
			MAX-ACCESS read-write
			STATUS current
			DESCRIPTION
				"Reboot the standby smm,"
			DEFVAL { 0 }
			::= { smm 79 }

		
		smmTrapFormat OBJECT-TYPE
			SYNTAX INTEGER
			MAX-ACCESS read-write
			STATUS current
			DESCRIPTION
				"Set and Get Trap Format. 0: Event code mode  1: OID mode"
			DEFVAL { 0 }
			::= { smm 80 }

		
		smmFaultDetectSwitch OBJECT-TYPE
			SYNTAX INTEGER
				{
				disable(0),
				enable(1)
				}
			MAX-ACCESS read-write
			STATUS current
			DESCRIPTION
				" Get or set fault detect switch."
			::= { smm 81 }
			
			
		smmUserSnmppasswd OBJECT-TYPE
			SYNTAX DisplayString
			MAX-ACCESS read-write
			STATUS current
			DESCRIPTION
				"change snmp password"
			::= { smm 82 }

		
		smmPasswdvalidPeriod OBJECT-TYPE
			SYNTAX DisplayString
			MAX-ACCESS read-write
			STATUS current
			DESCRIPTION
				"change snmp password"
			::= { smm 83 }

		
		smmSnmpSwitchss OBJECT-TYPE
			SYNTAX INTEGER
				{
				disable(1),
				enable(2)
				}
			MAX-ACCESS read-write
			STATUS current
			DESCRIPTION
				"Used to set or query SNMP Switchs enabled status.
				1 - disable
				2 - enable"
			::= { smm 84 }
		
	
		smmKVMServerPort OBJECT-TYPE
			SYNTAX OCTET STRING
			MAX-ACCESS read-write
			STATUS current
			DESCRIPTION
				"Get or set KVM server Port.
 	            settable format:
 	            management port,data transfer port
 	            for example:2198,2200"
			::= { smm 98 }

		
		
		smmVMMServerPort OBJECT-TYPE
			SYNTAX OCTET STRING
			MAX-ACCESS read-write
			STATUS current
			DESCRIPTION
				"Get or set VMM server Port.
				 settable format:Port number
 	             for example:8501"
			::= { smm 99 }
			
		smmSensorTargetTable OBJECT-TYPE
			SYNTAX SEQUENCE OF SmmSensorTargetEntry
			MAX-ACCESS not-accessible
			STATUS current
			DESCRIPTION
				"A table containing the list of sensor information."
			::= { smm 2001 }

		
 		smmSensorTargetEntry OBJECT-TYPE
			SYNTAX SmmSensorTargetEntry
			MAX-ACCESS not-accessible
			STATUS current
			DESCRIPTION
				"Information about a particular current sensor."
			INDEX { smmTarget }
			::= { smmSensorTargetTable 1 }
		
		SmmSensorTargetEntry ::=
			SEQUENCE { 
				smmTarget
					DisplayString,
				smmCurrent
					DisplayString,
				smmThresholdsAll
					DisplayString,
				smmUpperCritical
					DisplayString,
				smmUpperNonCritical
					DisplayString,
				smmUpperNonRecoverable
					DisplayString,
				smmLowerNonCritical
					DisplayString,
				smmLowerCritical
					DisplayString,
				smmLowerNonRecoverable
					DisplayString,
				smmSensorHealth
					INTEGER,
				smmSensorHealthEvents
					DisplayString,
				smmNegativeHysteresis
					DisplayString,
				smmPositiveHysteresis
					DisplayString,
				smmSensorType
					DisplayString,
				smmSensorFRUInfo
					DisplayString
			 }

 		smmTarget OBJECT-TYPE
			SYNTAX DisplayString
			MAX-ACCESS not-accessible
			STATUS current
			DESCRIPTION
				" "
			::= { smmSensorTargetEntry 1 }
		
 		smmCurrent OBJECT-TYPE
			SYNTAX DisplayString
			MAX-ACCESS read-only
			STATUS current
			DESCRIPTION
				"Display the current value of a sensor."
			::= { smmSensorTargetEntry 2 }
		
 		smmThresholdsAll OBJECT-TYPE
			SYNTAX DisplayString
			MAX-ACCESS read-only
			STATUS current
			DESCRIPTION
				"All thresholds of a sensor"
			::= { smmSensorTargetEntry 3 }
		
 		smmUpperCritical OBJECT-TYPE
			SYNTAX DisplayString
			MAX-ACCESS read-write
			STATUS current
			DESCRIPTION
				"Upper critical thresholds"
			::= { smmSensorTargetEntry 4 }
		
 		smmUpperNonCritical OBJECT-TYPE
			SYNTAX DisplayString
			MAX-ACCESS read-write
			STATUS current
			DESCRIPTION
				"Upper non-critical thresholds"
			::= { smmSensorTargetEntry 5 }
		
 		smmUpperNonRecoverable OBJECT-TYPE
			SYNTAX DisplayString
			MAX-ACCESS read-write
			STATUS current
			DESCRIPTION
				"Upper non-recoverable thresholds"
			::= { smmSensorTargetEntry 6 }
		
 		smmLowerNonCritical OBJECT-TYPE
			SYNTAX DisplayString
			MAX-ACCESS read-write
			STATUS current
			DESCRIPTION
				"Lower non-critical thresholds"
			::= { smmSensorTargetEntry 7 }
		
 		smmLowerCritical OBJECT-TYPE
			SYNTAX DisplayString
			MAX-ACCESS read-write
			STATUS current
			DESCRIPTION
				"Lower critical thresholds"
			::= { smmSensorTargetEntry 8 }
		
 		smmLowerNonRecoverable OBJECT-TYPE
			SYNTAX DisplayString
			MAX-ACCESS read-write
			STATUS current
			DESCRIPTION
				"Lower non-recoverable thresholds"
			::= { smmSensorTargetEntry 9 }
		
 		smmSensorHealth OBJECT-TYPE
			SYNTAX INTEGER
				{
				ok(0),
				minor(1),
				major(2),
				critical(3)
				}
			MAX-ACCESS read-only
			STATUS current
			DESCRIPTION
				"smmHealth information about a particular smmLocation. 
				This will be one of the following:
				(0-ok, 1-minor, 2-major, 3-critical)"
			::= { smmSensorTargetEntry 14 }
		
 		smmSensorHealthEvents OBJECT-TYPE
			SYNTAX DisplayString
			MAX-ACCESS read-only
			STATUS current
			DESCRIPTION
				"Events that contribute to the smmHealth of the smmLocation.  
				This is a list of events currently happening on the 
				smmLocation."
			::= { smmSensorTargetEntry 15 }
		
 		smmNegativeHysteresis OBJECT-TYPE
			SYNTAX DisplayString
			MAX-ACCESS read-write
			STATUS current
			DESCRIPTION
				"Get/Set the negativeHysteresis value"
			::= { smmSensorTargetEntry 16 }
		
 		smmPositiveHysteresis OBJECT-TYPE
			SYNTAX DisplayString
			MAX-ACCESS read-write
			STATUS current
			DESCRIPTION
				"Get/Set the positiveHysteresis value"
			::= { smmSensorTargetEntry 17 }
		
 		smmSensorType OBJECT-TYPE
			SYNTAX DisplayString
			MAX-ACCESS read-only
			STATUS current
			DESCRIPTION
				"Get the type of the sensor"
			::= { smmSensorTargetEntry 18 }
		
 		smmSensorFRUInfo OBJECT-TYPE
			SYNTAX DisplayString
			MAX-ACCESS read-only
			STATUS current
			DESCRIPTION
				"Get the fruinfo of the sensor"
			::= { smmSensorTargetEntry 19 }
		
 		smmFruTable OBJECT-TYPE
			SYNTAX SEQUENCE OF SmmFruEntry
			MAX-ACCESS not-accessible
			STATUS current
			DESCRIPTION
				"A table containing the list of FRU information."
			::= { smm 2002 }
		
 		smmFruEntry OBJECT-TYPE
			SYNTAX SmmFruEntry
			MAX-ACCESS not-accessible
			STATUS current
			DESCRIPTION
				"Information about a particular current sensor."
			INDEX { smmfruNumber }
			::= { smmFruTable 1 }
		
		SmmFruEntry ::=
			SEQUENCE { 
				smmfruNumber
					INTEGER,
				smmFruHotSwapState
					DisplayString,
				smmFruLabel
					DisplayString,
				smmDeleteFruLabel
					DisplayString,
				smmResetReason
					DisplayString
			 }

 		smmfruNumber OBJECT-TYPE
			SYNTAX INTEGER
			MAX-ACCESS not-accessible
			STATUS current
			DESCRIPTION
				" "
			::= { smmFruEntry 1 }
		
 		smmFruHotSwapState OBJECT-TYPE
			SYNTAX DisplayString
			MAX-ACCESS read-only
			STATUS current
			DESCRIPTION
				"Retrieve the hot swap state of the FRU from the SMM's 
				internally known hot swap states.  Value indicating 
				the ATCA defined M state (0=> M0, 1=>M1 etc)"
			::= { smmFruEntry 3 }

		
		smmFruLabel OBJECT-TYPE
			SYNTAX DisplayString
			MAX-ACCESS read-write
			STATUS current
			DESCRIPTION
				"Get or set smm fru label.
				When set,the format of the setting is like this:
				labelname=label.
				The lenth of the string should be <= 620 bytes.
				The lenth of labelname should be <= 61 bytes."
			::= { smmFruEntry 10 }
		
 		smmDeleteFruLabel OBJECT-TYPE
			SYNTAX DisplayString
			MAX-ACCESS read-write
			STATUS current
			DESCRIPTION
				"Delete fru label of smm."
			::= { smmFruEntry 11 }
		
 		smmResetReason OBJECT-TYPE
			SYNTAX DisplayString
			MAX-ACCESS read-only
			STATUS current
			DESCRIPTION
				"Delete fru label of smm."
			::= { smmFruEntry 12 }
		
 		smmFruLedTable OBJECT-TYPE
			SYNTAX SEQUENCE OF SmmFruLedEntry
			MAX-ACCESS not-accessible
			STATUS current
			DESCRIPTION
				"A table containing the list of led information."
			::= { smm 2003 }
		
 		smmFruLedEntry OBJECT-TYPE
			SYNTAX SmmFruLedEntry
			MAX-ACCESS not-accessible
			STATUS current
			DESCRIPTION
				"Information about a particular current led."
			INDEX { smmFruID, smmFruLed }
			::= { smmFruLedTable 1 }
		
		SmmFruLedEntry ::=
			SEQUENCE { 
				smmFruID
					INTEGER,
				smmFruLed
					DisplayString,
				smmFruLedColorProps
					DisplayString,
				smmFruLedState
					DisplayString
			 }

 		smmFruID OBJECT-TYPE
			SYNTAX INTEGER
			MAX-ACCESS not-accessible
			STATUS current
			DESCRIPTION
				"smm led's INDEX"
			::= { smmFruLedEntry 1 }
		
 		smmFruLed OBJECT-TYPE
			SYNTAX DisplayString
			MAX-ACCESS not-accessible
			STATUS current
			DESCRIPTION
				" "
			::= { smmFruLedEntry 2 }
		
 		smmFruLedColorProps OBJECT-TYPE
			SYNTAX DisplayString
			MAX-ACCESS read-only
			STATUS current
			DESCRIPTION
				"Finds out what colors are supported by the LED"
			::= { smmFruLedEntry 3 }
		
 		smmFruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { smmFruLedEntry 4 }
		
 		smmFruDescriptionTable OBJECT-TYPE
			SYNTAX SEQUENCE OF SmmFruDescriptionEntry
			MAX-ACCESS not-accessible
			STATUS current
			DESCRIPTION
				"A table containing the list of SMM FRU information."
			::= { smm 2004 }
		
 		smmFruDescriptionEntry OBJECT-TYPE
			SYNTAX SmmFruDescriptionEntry
			MAX-ACCESS not-accessible
			STATUS current
			DESCRIPTION
				"Information about a particular current FRU."
			INDEX { smmfruNum }
			::= { smmFruDescriptionTable 1 }
		
		SmmFruDescriptionEntry ::=
			SEQUENCE { 
				smmfruNum
					INTEGER,
				smmfruBoardDescription
					DisplayString,
				smmfruBoardManufacturer
					DisplayString,
				smmfruBoardPartNumber
					DisplayString,
				smmfruBoardSerialNumber
					DisplayString,
				smmfruBoardManufactureDate
					DisplayString,
				smmfruProductDescription
					DisplayString,
				smmfruProductManufacturer
					DisplayString,
				smmfruProductPartNumber
					DisplayString,
				smmfruProductSerialNumber
					DisplayString,
				smmfruProductRevision
					DisplayString,
				smmfruAll
					DisplayString
			 }

 		smmfruNum OBJECT-TYPE
			SYNTAX INTEGER
			MAX-ACCESS not-accessible
			STATUS current
			DESCRIPTION
				"FRU's INDEX"
			::= { smmFruDescriptionEntry 1 }
		
 		smmfruBoardDescription OBJECT-TYPE
			SYNTAX DisplayString
			MAX-ACCESS read-write
			STATUS current
			DESCRIPTION
				"Used to read the Board Description from the Fru."
			::= { smmFruDescriptionEntry 2 }
		
 		smmfruBoardManufacturer OBJECT-TYPE
			SYNTAX DisplayString
			MAX-ACCESS read-only
			STATUS current
			DESCRIPTION
				"Used to read the Board Manufacturer from the Fru."
			::= { smmFruDescriptionEntry 3 }
		
 		smmfruBoardPartNumber OBJECT-TYPE
			SYNTAX DisplayString
			MAX-ACCESS read-only
			STATUS current
			DESCRIPTION
				"Used to read the Board Part Number from the Fru."
			::= { smmFruDescriptionEntry 4 }
		
 		smmfruBoardSerialNumber OBJECT-TYPE
			SYNTAX DisplayString
			MAX-ACCESS read-write
			STATUS current
			DESCRIPTION
				"Used to read the Board Serial Number from the Fru."
			::= { smmFruDescriptionEntry 5 }
		
 		smmfruBoardManufactureDate OBJECT-TYPE
			SYNTAX DisplayString
			MAX-ACCESS read-write
			STATUS current
			DESCRIPTION
				"Used to read the Board Manufacture Date from the Fru."
			::= { smmFruDescriptionEntry 6 }
		
 		smmfruProductDescription OBJECT-TYPE
			SYNTAX DisplayString
			MAX-ACCESS read-only
			STATUS current
			DESCRIPTION
				"Used to read the Product Description from the Fru."
			::= { smmFruDescriptionEntry 7 }
		
 		smmfruProductManufacturer OBJECT-TYPE
			SYNTAX DisplayString
			MAX-ACCESS read-only
			STATUS current
			DESCRIPTION
				"Used to read the Product Manufacturer from the Fru."
			::= { smmFruDescriptionEntry 8 }
		
 		smmfruProductPartNumber OBJECT-TYPE
			SYNTAX DisplayString
			MAX-ACCESS read-only
			STATUS current
			DESCRIPTION
				"Used to read the Product Part Number from the Fru."
			::= { smmFruDescriptionEntry 9 }
		
 		smmfruProductSerialNumber OBJECT-TYPE
			SYNTAX DisplayString
			MAX-ACCESS read-only
			STATUS current
			DESCRIPTION
				"Used to read the Product Serial Number from the Fru."
			::= { smmFruDescriptionEntry 10 }
		
 		smmfruProductRevision OBJECT-TYPE
			SYNTAX DisplayString
			MAX-ACCESS read-only
			STATUS current
			DESCRIPTION
				"Used to read the Product Revision from the Fru."
			::= { smmFruDescriptionEntry 13 }
		
 		smmfruAll OBJECT-TYPE
			SYNTAX DisplayString
			MAX-ACCESS read-only
			STATUS current
			DESCRIPTION
				"Used to read fru info all."
			::= { smmFruDescriptionEntry 14 }
		
 		smmNetworkConfigTable OBJECT-TYPE
			SYNTAX SEQUENCE OF SmmNetworkConfigEntry
			MAX-ACCESS not-accessible
			STATUS current
			DESCRIPTION
				"A table containing the list of SMM network information."
			::= { smm 2005 }
		
 		smmNetworkConfigEntry OBJECT-TYPE
			SYNTAX SmmNetworkConfigEntry
			MAX-ACCESS not-accessible
			STATUS current
			DESCRIPTION
				"Information about a particular current eth."
			INDEX { smmEthNum }
			::= { smmNetworkConfigTable 1 }
		
		SmmNetworkConfigEntry ::=
			SEQUENCE { 
				smmEthNum
					INTEGER,
				smmFloatIpAddr
					DisplayString,
				smmStaticIpAddr
					DisplayString,
				smmAllIpAddr
					DisplayString,
				smmDeleteIpAddr
					DisplayString,
				smmEthMac
					DisplayString,
				smmFloatIpgateway
					DisplayString,
				smmStaticIpgateway
					DisplayString,
				smmStandbyIpAddr
					DisplayString
			 }

 		smmEthNum OBJECT-TYPE
			SYNTAX INTEGER
			MAX-ACCESS not-accessible
			STATUS current
			DESCRIPTION
				"ETH's INDEX."
			::= { smmNetworkConfigEntry 1 }
		
 		smmFloatIpAddr OBJECT-TYPE
			SYNTAX DisplayString
			MAX-ACCESS read-write
			STATUS current
			DESCRIPTION
				"Used to get or set the float IP address of ethX.
				settable format:
				Ipaddress,Mask,BroadcastAddress"
			::= { smmNetworkConfigEntry 2 }
		
 		smmStaticIpAddr OBJECT-TYPE
			SYNTAX DisplayString
			MAX-ACCESS read-write
			STATUS current
			DESCRIPTION
				"Used to get or set the static IP address of ethX.
				settable format:
				Ipaddress,Mask,BroadcastAddress"
			::= { smmNetworkConfigEntry 3 }
		
 		smmAllIpAddr OBJECT-TYPE
			SYNTAX DisplayString
			MAX-ACCESS read-only
			STATUS current
			DESCRIPTION
				"Used to get ALL IP addresses of ethX."
			::= { smmNetworkConfigEntry 4 }
		
 		smmDeleteIpAddr OBJECT-TYPE
			SYNTAX DisplayString
			MAX-ACCESS read-write
			STATUS current
			DESCRIPTION
				"Delete IP address of ethX."
			::= { smmNetworkConfigEntry 5 }
		
 		smmEthMac OBJECT-TYPE
			SYNTAX DisplayString
			MAX-ACCESS read-only
			STATUS current
			DESCRIPTION
				"Get Eth MAC"
			::= { smmNetworkConfigEntry 7 }
		
		smmFloatIpgateway OBJECT-TYPE
			SYNTAX DisplayString
			MAX-ACCESS read-write
			STATUS current
			DESCRIPTION
				"Used to get or set the float IP gateway of ethX. 
				settable format:
				Ipaddress,Mask,Gateway"
			::= { smmNetworkConfigEntry 8 }
		
		smmStaticIpgateway OBJECT-TYPE
			SYNTAX DisplayString
			MAX-ACCESS read-write
			STATUS current
			DESCRIPTION
				"Used to get or set the static IP gateway of ethX. .
				settable format:
				Ipaddress,Mask,Gateway"
			::= { smmNetworkConfigEntry 9 }
			
		smmStandbyIpAddr OBJECT-TYPE
			SYNTAX DisplayString
			MAX-ACCESS read-write
			STATUS current
			DESCRIPTION
				"Used to get or set the standby smm static IP address of ethX.
				settable format:
				Ipaddress,Mask,BroadcastAddress"
			::= { smmNetworkConfigEntry 10 }
		
		
		smmDomainTable OBJECT-TYPE
			SYNTAX SEQUENCE OF SmmDomainEntry
			MAX-ACCESS not-accessible
			STATUS current
			DESCRIPTION
				"A table containing the list of SMM Domain information."
			::= { smm 2006 }
		
	
		smmDomainEntry OBJECT-TYPE
			SYNTAX SmmDomainEntry
			MAX-ACCESS not-accessible
			STATUS current
			DESCRIPTION
				"Information about a particular current smmDomain."
			INDEX { smmDomainName }
			::= { smmDomainTable 1 }
		
		SmmDomainEntry ::=
			SEQUENCE { 
				smmDomainName
					DisplayString,
				smmDomainUsers
					DisplayString,
				smmDomainSlots
					DisplayString,
				smmDomainAlias
					DisplayString
			 }

		
		smmDomainName OBJECT-TYPE
			SYNTAX DisplayString
			MAX-ACCESS read-write
			STATUS current
			DESCRIPTION
				"Name of the domain."
			::= { smmDomainEntry 1 }

		
	
		smmDomainUsers OBJECT-TYPE
			SYNTAX DisplayString
			MAX-ACCESS read-write
			STATUS current
			DESCRIPTION
				"Users under the domain.
				settable format:
				username,newDomainName"
			::= { smmDomainEntry 2 }

		
	
		smmDomainSlots OBJECT-TYPE
			SYNTAX DisplayString
			MAX-ACCESS read-write
			STATUS current
			DESCRIPTION
				"Slots under the domain."
			::= { smmDomainEntry 3 }

		

		smmDomainAlias OBJECT-TYPE
			SYNTAX DisplayString
			MAX-ACCESS read-write
			STATUS current
			DESCRIPTION
				"Alias of the domain."
			::= { smmDomainEntry 4 }
		
		smmRemoteSyslogTable OBJECT-TYPE
			SYNTAX SEQUENCE OF SmmRemoteSyslogEntry
			MAX-ACCESS not-accessible
			STATUS current
			DESCRIPTION
				"A table containing the remote syslog configurations."
			::= { smm 2007 }
		
		smmRemoteSyslogEntry OBJECT-TYPE
			SYNTAX SmmRemoteSyslogEntry
			MAX-ACCESS not-accessible
			STATUS current
			DESCRIPTION
				"Information about remote syslog configurations."
			INDEX { smmRemoteSyslogTarget }
			::= { smmRemoteSyslogTable 1 }
		
		SmmRemoteSyslogEntry ::=
			SEQUENCE { 
				smmRemoteSyslogTarget
					INTEGER,
				smmRemoteSyslogState
					INTEGER,
				smmRemoteSyslogServerAddress
					DisplayString,
				smmRemoteSyslogServerPort
					INTEGER,
				smmRemoteSyslogProtocol
					INTEGER,
				smmRemoteSyslogLevel
					INTEGER,
				smmRemoteSyslogTransport
					INTEGER,
				smmRemoteSyslogServerCA
					DisplayString,
				smmRemoteSyslogAuth
					INTEGER,
				smmRemoteSyslogClientCertificate
					DisplayString
			 }

		smmRemoteSyslogTarget OBJECT-TYPE
			SYNTAX INTEGER
			MAX-ACCESS not-accessible
			STATUS current
			DESCRIPTION
				" Specify Traget: operation log(1) or system log(2)"
			::= { smmRemoteSyslogEntry 1 }
		
		smmRemoteSyslogState OBJECT-TYPE
			SYNTAX INTEGER (1..2)
			MAX-ACCESS read-write
			STATUS current
			DESCRIPTION
				"Query and set remote syslog status: disable(1), enable(2)"
			::= { smmRemoteSyslogEntry 2 }
		
		smmRemoteSyslogServerAddress OBJECT-TYPE
			SYNTAX DisplayString
			MAX-ACCESS read-write
			STATUS current
			DESCRIPTION
				"Query and set the syslog server address"
			::= { smmRemoteSyslogEntry 3 }
		
		smmRemoteSyslogServerPort OBJECT-TYPE
			SYNTAX INTEGER (1..65535)
			MAX-ACCESS read-write
			STATUS current
			DESCRIPTION
				"Query and set the syslog server port"
			::= { smmRemoteSyslogEntry 4 }
		
		smmRemoteSyslogProtocol OBJECT-TYPE
			SYNTAX INTEGER (1..2)
			MAX-ACCESS read-write
			STATUS current
			DESCRIPTION
				"Query and set the syslog protocol: BSD-syslog(1) or IETF-syslog(2)"
			::= { smmRemoteSyslogEntry 5 }
		
		smmRemoteSyslogLevel OBJECT-TYPE
			SYNTAX INTEGER (1..4)
			MAX-ACCESS read-write
			STATUS current
			DESCRIPTION
				"Query and set the log level, only available to system log: all(1), minor(2), major(3), critical(4)"
			::= { smmRemoteSyslogEntry 6 }
		
		smmRemoteSyslogTransport OBJECT-TYPE
			SYNTAX INTEGER (1..3)
			MAX-ACCESS read-write
			STATUS current
			DESCRIPTION
				"Query and set the transport protocol: TLS(1), TCP(2), UDP(3)."
			::= { smmRemoteSyslogEntry 7 }
		
		smmRemoteSyslogServerCA OBJECT-TYPE
			SYNTAX DisplayString
			MAX-ACCESS read-write
			STATUS current
			DESCRIPTION
				"Query and set the syslog server certificate"
			::= { smmRemoteSyslogEntry 8 }
		
		smmRemoteSyslogAuth OBJECT-TYPE
			SYNTAX INTEGER (1..2)
			MAX-ACCESS read-write
			STATUS current
			DESCRIPTION
				"Query and set the authentication way: One-way authentication(1), Two-way authentication(2)."
			::= { smmRemoteSyslogEntry 9 }
		
		smmRemoteSyslogClientCertificate OBJECT-TYPE
			SYNTAX DisplayString
			MAX-ACCESS read-write
			STATUS current
			DESCRIPTION
				"Query and set the client certificate"
			::= { smmRemoteSyslogEntry 10 }
		
		blades OBJECT IDENTIFIER ::= { hwSMM 4 }
		
 		blade1 OBJECT IDENTIFIER ::= { blades 1 }
		
		
 		b1DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade1 4 }
		
 		b1PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade1 5 }
		
 		b1Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade1 6 }

		
 		b1Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade1 8 }
		
 		b1HealthEvents OBJECT-TYPE
			SYNTAX DisplayString
			MAX-ACCESS read-only
			STATUS current
			DESCRIPTION
				"Events that contribute to the b1Health of the b1Location.  
				This is a list of events currently happening on the 
				b1Location."
			::= { blade1 9 }
		
 		b1ClearSEL OBJECT-TYPE
			SYNTAX INTEGER { clear(1) }
			MAX-ACCESS read-write
			STATUS current
			DESCRIPTION
				"Clean the BMC's SEL on the board."
			::= { blade1 12 }
		
 		b1ExDiskBoardPresence OBJECT-TYPE
			SYNTAX INTEGER
				{
				not-present(0),
				present(1)
				}
			MAX-ACCESS read-only
			STATUS current
			DESCRIPTION
				"Used to find out if the extended disk board is present.
				0 - not present
				1 - present"
			::= { blade1 14 }
		
 		b1BladeVersion OBJECT-TYPE
			SYNTAX DisplayString
			MAX-ACCESS read-only
			STATUS current
			DESCRIPTION
				"display the Version of board1."
			::= { blade1 20 }
		
 		b1MACAddress OBJECT-TYPE
			SYNTAX DisplayString
			MAX-ACCESS read-only
			STATUS current
			DESCRIPTION
				"display the MACAddress of board1."
			::= { blade1 21 }
		
				
							
		
 		b1Safepwofftime OBJECT-TYPE
			SYNTAX INTEGER
			MAX-ACCESS read-write
			STATUS current
			DESCRIPTION
				"the safe poweroff time.
				"
			::= { blade1 26 }
		
 		b1BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]   
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]   
				6=Force boot into BIOS Setup
				15=Force boot from Floppy/primary removable media           
				
				"
			::= { blade1 32 }
		
 		b1Systeminfo OBJECT-TYPE
			SYNTAX DisplayString
			MAX-ACCESS read-write
			STATUS current
			DESCRIPTION
				"display the system information of board1."
			::= { blade1 36 }

		
 		b1SystemProperties OBJECT-TYPE
			SYNTAX DisplayString
			MAX-ACCESS read-only
			STATUS current
			DESCRIPTION
				"Get the power of blade1."
			::= { blade1 39 }
		
 		b1BiosCfg OBJECT-TYPE
			SYNTAX DisplayString
			MAX-ACCESS read-write
			STATUS current
			DESCRIPTION
				"Get the power of blade1."
			::= { blade1 40 }
		
 		b1WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade1 41 }
		
 		b1RealTimePower OBJECT-TYPE
			SYNTAX INTEGER
			MAX-ACCESS read-only
			STATUS current
			DESCRIPTION
				" "
			::= { blade1 43 }
		
 		b1PowerCapping OBJECT-TYPE
			SYNTAX DisplayString
			MAX-ACCESS read-write
			STATUS current
			DESCRIPTION
				" "
			::= { blade1 44 }
		
 		b1Powerreference OBJECT-TYPE
			SYNTAX INTEGER
			MAX-ACCESS read-only
			STATUS current
			DESCRIPTION
				" "
			::= { blade1 45 }
		
 		b1ClearBiosConfig OBJECT-TYPE
			SYNTAX INTEGER
			MAX-ACCESS read-write
			STATUS current
			DESCRIPTION
				" "
			::= { blade1 46 }
		
 		b1BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade1 47 }
		
 		b1BmcUserAdd OBJECT-TYPE
			SYNTAX DisplayString
			MAX-ACCESS read-write
			STATUS current
			DESCRIPTION
				"Used to Add the BMC User
				settable format:
				username,passwd"
			::= { blade1 48 }
		
 		b1BmcUserDel OBJECT-TYPE
			SYNTAX DisplayString
			MAX-ACCESS read-write
			STATUS current
			DESCRIPTION
				"Used to Del the BMC User
				settable format:
				username"
			::= { blade1 49 }
		
 		b1BmcUserPasswd OBJECT-TYPE
			SYNTAX DisplayString
			MAX-ACCESS read-write
			STATUS current
			DESCRIPTION
				"Used to Change the BMC User Passwd
				settable format:
				username,passwd"
			::= { blade1 50 }
		
 		b1BmcUserpropertychg OBJECT-TYPE
			SYNTAX DisplayString
			MAX-ACCESS read-write
			STATUS current
			DESCRIPTION
				"Used to Change the BMC User Property
				settable format:
				username,property"
			::= { blade1 51 }
		
 		b1BmcGateway OBJECT-TYPE
			SYNTAX DisplayString
			MAX-ACCESS read-write
			STATUS current
			DESCRIPTION
				"Read or set the gateway."
			::= { blade1 52 }
		
 		b1SlotBitmap OBJECT-TYPE
			SYNTAX INTEGER
			MAX-ACCESS read-only
			STATUS current
			DESCRIPTION
				" "
			::= { blade1 55 }
		
		b1systemGuid OBJECT-TYPE
			SYNTAX DisplayString
			MAX-ACCESS read-only
			STATUS current
			DESCRIPTION
				" "
			::= { blade1 56 }
		
		b1ProductName OBJECT-TYPE
			SYNTAX DisplayString
			MAX-ACCESS read-only
			STATUS current
			DESCRIPTION
				"display the Version of board1."
			::= { blade1 57 }
		
		b1BundleVersion OBJECT-TYPE
			SYNTAX DisplayString
			MAX-ACCESS read-write
			STATUS current
			DESCRIPTION
				"Get or set the board1 bundle version."
			::= { blade1 58 }

		blade1SensorTargetTable OBJECT-TYPE
			SYNTAX SEQUENCE OF Blade1SensorTargetEntry
			MAX-ACCESS not-accessible
			STATUS current
			DESCRIPTION
				"A table containing the list of sensor information."
			::= { blade1 2001 }
		
 		blade1SensorTargetEntry OBJECT-TYPE
			SYNTAX Blade1SensorTargetEntry
			MAX-ACCESS not-accessible
			STATUS current
			DESCRIPTION
				"Information about a particular current sensor."
			INDEX { b1Target }
			::= { blade1SensorTargetTable 1 }
		
		Blade1SensorTargetEntry ::=
			SEQUENCE { 
				b1Target
					DisplayString,
				b1Current
					DisplayString,
				b1ThresholdsAll
					DisplayString,
				b1UpperCritical
					DisplayString,
				b1UpperNonCritical
					DisplayString,
				b1UpperNonRecoverable
					DisplayString,
				b1LowerNonCritical
					DisplayString,
				b1LowerCritical
					DisplayString,
				b1LowerNonRecoverable
					DisplayString,
				b1SensorHealth
					INTEGER,
				b1SensorHealthEvents
					DisplayString,
				b1NegativeHysteresis
					DisplayString,
				b1PositiveHysteresis
					DisplayString,
				b1SensorType
					DisplayString,
				b1SensorFRUInfo
					DisplayString
			 }

 		b1Target OBJECT-TYPE
			SYNTAX DisplayString
			MAX-ACCESS not-accessible
			STATUS current
			DESCRIPTION
				"sensor Name"
			::= { blade1SensorTargetEntry 1 }
		
 		b1Current OBJECT-TYPE
			SYNTAX DisplayString
			MAX-ACCESS read-only
			STATUS current
			DESCRIPTION
				"Display the current value of a sensor."
			::= { blade1SensorTargetEntry 2 }
		
 		b1ThresholdsAll OBJECT-TYPE
			SYNTAX DisplayString
			MAX-ACCESS read-only
			STATUS current
			DESCRIPTION
				"All thresholds of a sensor"
			::= { blade1SensorTargetEntry 3 }
		
 		b1UpperCritical OBJECT-TYPE
			SYNTAX DisplayString
			MAX-ACCESS read-write
			STATUS current
			DESCRIPTION
				"Upper critical thresholds"
			::= { blade1SensorTargetEntry 4 }
		
 		b1UpperNonCritical OBJECT-TYPE
			SYNTAX DisplayString
			MAX-ACCESS read-write
			STATUS current
			DESCRIPTION
				"Upper non-critical thresholds"
			::= { blade1SensorTargetEntry 5 }
		
 		b1UpperNonRecoverable OBJECT-TYPE
			SYNTAX DisplayString
			MAX-ACCESS read-write
			STATUS current
			DESCRIPTION
				"Upper non-recoverable thresholds"
			::= { blade1SensorTargetEntry 6 }
		
 		b1LowerNonCritical OBJECT-TYPE
			SYNTAX DisplayString
			MAX-ACCESS read-write
			STATUS current
			DESCRIPTION
				"Lower non-critical thresholds"
			::= { blade1SensorTargetEntry 7 }
		
 		b1LowerCritical OBJECT-TYPE
			SYNTAX DisplayString
			MAX-ACCESS read-write
			STATUS current
			DESCRIPTION
				"Lower critical thresholds"
			::= { blade1SensorTargetEntry 8 }
		
 		b1LowerNonRecoverable OBJECT-TYPE
			SYNTAX DisplayString
			MAX-ACCESS read-write
			STATUS current
			DESCRIPTION
				"Lower non-recoverable thresholds"
			::= { blade1SensorTargetEntry 9 }
		
 		b1SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade1SensorTargetEntry 10 }
		
 		b1SensorHealthEvents OBJECT-TYPE
			SYNTAX DisplayString
			MAX-ACCESS read-only
			STATUS current
			DESCRIPTION
				"Events that contribute to the b1Health of the b1Location.  
				This is a list of events currently happening on the 
				b1Location."
			::= { blade1SensorTargetEntry 11 }
		
		
 		b1NegativeHysteresis OBJECT-TYPE
			SYNTAX DisplayString
			MAX-ACCESS read-write
			STATUS current
			DESCRIPTION
				"Get/Set the negativeHysteresis value."
			::= { blade1SensorTargetEntry 16 }
		
 		b1PositiveHysteresis OBJECT-TYPE
			SYNTAX DisplayString
			MAX-ACCESS read-write
			STATUS current
			DESCRIPTION
				"Get/Set the positiveHysteresis value."
			::= { blade1SensorTargetEntry 17 }
		
 		b1SensorType OBJECT-TYPE
			SYNTAX DisplayString
			MAX-ACCESS read-only
			STATUS current
			DESCRIPTION
				"Get the type of the sensor."
			::= { blade1SensorTargetEntry 18 }
		
 		b1SensorFRUInfo OBJECT-TYPE
			SYNTAX DisplayString
			MAX-ACCESS read-only
			STATUS current
			DESCRIPTION
				"Get the fruinfo of the sensor."
			::= { blade1SensorTargetEntry 19 }
		
 		blade1FruTable OBJECT-TYPE
			SYNTAX SEQUENCE OF Blade1FruEntry
			MAX-ACCESS not-accessible
			STATUS current
			DESCRIPTION
				"A table containing the list of FRU information."
			::= { blade1 2002 }
		
 		blade1FruEntry OBJECT-TYPE
			SYNTAX Blade1FruEntry
			MAX-ACCESS not-accessible
			STATUS current
			DESCRIPTION
				"Information about a particular current FRU."
			INDEX { b1fruNumber }
			::= { blade1FruTable 1 }
		
		Blade1FruEntry ::=
			SEQUENCE { 
				b1fruNumber
					INTEGER,
				b1FruHotSwapState
					DisplayString,
				b1FruLedProperties
					DisplayString,
				b1FRUControl
					INTEGER,
				b1FRULabel
					DisplayString,
				b1ResetReason
					DisplayString
			 }

 		b1fruNumber OBJECT-TYPE
			SYNTAX INTEGER
			MAX-ACCESS not-accessible
			STATUS current
			DESCRIPTION
				" "
			::= { blade1FruEntry 1 }
		
 		b1FruHotSwapState OBJECT-TYPE
			SYNTAX DisplayString
			MAX-ACCESS read-only
			STATUS current
			DESCRIPTION
				"Retrieve the hot swap state of the FRU from the 
				internally known hot swap states of blade1."
			::= { blade1FruEntry 3 }
		
 		b1FruLedProperties OBJECT-TYPE
			SYNTAX DisplayString
			MAX-ACCESS read-only
			STATUS current
			DESCRIPTION
				"Retrieves the LED support information from a FRU. Returns a comma separated
				list of LEDS and the number of FRU supported user LEDs."
			::= { blade1FruEntry 4 }

		

		b1FRUControl OBJECT-TYPE
			SYNTAX INTEGER
			MAX-ACCESS read-write
			STATUS current
			DESCRIPTION
				"Set the FRU to do things like Reset, Power Off Then On, etc.
				Settable value:
				'0' - reset
				'2' - power off then on
				'3' - interrupt control
				"
			::= { blade1FruEntry 9 }
		
 		b1FRULabel OBJECT-TYPE
			SYNTAX DisplayString
			MAX-ACCESS read-only
			STATUS current
			DESCRIPTION
				"Get fru label of blade1."
			::= { blade1FruEntry 10 }
		
 		b1ResetReason OBJECT-TYPE
			SYNTAX DisplayString
			MAX-ACCESS read-only
			STATUS current
			DESCRIPTION
				"Delete fru label of smm."
			::= { blade1FruEntry 11 }
		
 		blade1FruLedTable OBJECT-TYPE
			SYNTAX SEQUENCE OF Blade1FruLedEntry
			MAX-ACCESS not-accessible
			STATUS current
			DESCRIPTION
				"A table containing the list of led information."
			::= { blade1 2003 }
		
 		blade1FruLedEntry OBJECT-TYPE
			SYNTAX Blade1FruLedEntry
			MAX-ACCESS not-accessible
			STATUS current
			DESCRIPTION
				"Information about a particular current led."
			INDEX { b1FruID, b1FruLed }
			::= { blade1FruLedTable 1 }
		
		Blade1FruLedEntry ::=
			SEQUENCE { 
				b1FruID
					INTEGER,
				b1FruLed
					DisplayString,
				b1FruLedColorProps
					DisplayString,
				b1FruLedState
					DisplayString
			 }

 		b1FruID OBJECT-TYPE
			SYNTAX INTEGER
			MAX-ACCESS not-accessible
			STATUS current
			DESCRIPTION
				" "
			::= { blade1FruLedEntry 1 }
		
 		b1FruLed OBJECT-TYPE
			SYNTAX DisplayString
			MAX-ACCESS not-accessible
			STATUS current
			DESCRIPTION
				" "
			::= { blade1FruLedEntry 2 }
		
 		b1FruLedColorProps OBJECT-TYPE
			SYNTAX DisplayString
			MAX-ACCESS read-only
			STATUS current
			DESCRIPTION
				"Finds out what colors are supported by the LED"
			::= { blade1FruLedEntry 3 }
		
 		b1FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade1FruLedEntry 4 }
		
 		blade1FruDescriptionTable OBJECT-TYPE
			SYNTAX SEQUENCE OF Blade1FruDescriptionEntry
			MAX-ACCESS not-accessible
			STATUS current
			DESCRIPTION
				"A table containing the list of Blade1 FRU information."
			::= { blade1 2004 }
		
 		blade1FruDescriptionEntry OBJECT-TYPE
			SYNTAX Blade1FruDescriptionEntry
			MAX-ACCESS not-accessible
			STATUS current
			DESCRIPTION
				"Information about a particular current FRU."
			INDEX { b1fruNum }
			::= { blade1FruDescriptionTable 1 }
		
		Blade1FruDescriptionEntry ::=
			SEQUENCE { 
				b1fruNum
					INTEGER,
				b1fruBoardDescription
					DisplayString,
				b1fruBoardManufacturer
					DisplayString,
				b1fruBoardPartNumber
					DisplayString,
				b1fruBoardSerialNumber
					DisplayString,
				b1fruBoardManufactureDate
					DisplayString,
				b1fruProductDescription
					DisplayString,
				b1fruProductManufacturer
					DisplayString,
				b1fruProductPartNumber
					DisplayString,
				b1fruProductSerialNumber
					DisplayString,
				b1fruProductRevision
					DisplayString,
				b1fruAll
					DisplayString
			 }

 		b1fruNum OBJECT-TYPE
			SYNTAX INTEGER
			MAX-ACCESS not-accessible
			STATUS current
			DESCRIPTION
				"blade1 FRU's INDEX"
			::= { blade1FruDescriptionEntry 1 }
		
 		b1fruBoardDescription OBJECT-TYPE
			SYNTAX DisplayString
			MAX-ACCESS read-only
			STATUS current
			DESCRIPTION
				"Used to read the Board Description from the blade1 fru."
			::= { blade1FruDescriptionEntry 2 }
		
 		b1fruBoardManufacturer OBJECT-TYPE
			SYNTAX DisplayString
			MAX-ACCESS read-only
			STATUS current
			DESCRIPTION
				"Used to read the Board Manufacturer from the blade1 fru."
			::= { blade1FruDescriptionEntry 3 }
		
 		b1fruBoardPartNumber OBJECT-TYPE
			SYNTAX DisplayString
			MAX-ACCESS read-only
			STATUS current
			DESCRIPTION
				"Used to read the Board Part Number from the blade1 fru."
			::= { blade1FruDescriptionEntry 4 }
		
 		b1fruBoardSerialNumber OBJECT-TYPE
			SYNTAX DisplayString
			MAX-ACCESS read-only
			STATUS current
			DESCRIPTION
				"Used to read the Board Serial Number from the blade1 fru."
			::= { blade1FruDescriptionEntry 5 }
		
 		b1fruBoardManufactureDate OBJECT-TYPE
			SYNTAX DisplayString
			MAX-ACCESS read-only
			STATUS current
			DESCRIPTION
				"Used to read the Board Manufacture Date from the blade1 fru."
			::= { blade1FruDescriptionEntry 6 }
		
 		b1fruProductDescription OBJECT-TYPE
			SYNTAX DisplayString
			MAX-ACCESS read-only
			STATUS current
			DESCRIPTION
				"Used to read the Product Description from the blade1 fru."
			::= { blade1FruDescriptionEntry 7 }
		
 		b1fruProductManufacturer OBJECT-TYPE
			SYNTAX DisplayString
			MAX-ACCESS read-only
			STATUS current
			DESCRIPTION
				"Used to read the Product Manufacturer from the blade1 fru."
			::= { blade1FruDescriptionEntry 8 }
		
 		b1fruProductPartNumber OBJECT-TYPE
			SYNTAX DisplayString
			MAX-ACCESS read-only
			STATUS current
			DESCRIPTION
				"Used to read the Product Part Number from the blade1 fru."
			::= { blade1FruDescriptionEntry 9 }
		
 		b1fruProductSerialNumber OBJECT-TYPE
			SYNTAX DisplayString
			MAX-ACCESS read-only
			STATUS current
			DESCRIPTION
				"Used to read the Product Serial Number from the blade1 fru."
			::= { blade1FruDescriptionEntry 10 }
		
 		b1fruProductRevision OBJECT-TYPE
			SYNTAX DisplayString
			MAX-ACCESS read-only
			STATUS current
			DESCRIPTION
				"Used to read the Product Revision from the blade1 fru."
			::= { blade1FruDescriptionEntry 13 }
		
 		b1fruAll OBJECT-TYPE
			SYNTAX DisplayString
			MAX-ACCESS read-only
			STATUS current
			DESCRIPTION
				"Used to read the fru info all."
			::= { blade1FruDescriptionEntry 14 }
		
		blade1CPUTable OBJECT-TYPE
			SYNTAX SEQUENCE OF Blade1CPUEntry
			MAX-ACCESS not-accessible
			STATUS current
			DESCRIPTION
				"A table containing the list of Blade1 FRU information."
			::= { blade1 2006 }
		
		blade1CPUEntry OBJECT-TYPE
			SYNTAX Blade1CPUEntry
			MAX-ACCESS not-accessible
			STATUS current
			DESCRIPTION
				"Information about a particular current FRU."
			INDEX { b1CPUIndex }
			::= { blade1CPUTable 1 }
		
		Blade1CPUEntry ::=
			SEQUENCE { 
				b1CPUIndex
					INTEGER,
				b1CPUMark
					DisplayString,
				b1CPUInfo
					DisplayString,
				b1CPUPresent
					INTEGER,
				b1CPUHealth
					INTEGER,
				b1CPULocation
					DisplayString
			 }

		b1CPUIndex OBJECT-TYPE
			SYNTAX INTEGER
			MAX-ACCESS not-accessible
			STATUS current
			DESCRIPTION
				"CPU INDEX"
			::= { blade1CPUEntry 1 }
		
		b1CPUMark OBJECT-TYPE
			SYNTAX DisplayString
			MAX-ACCESS read-only
			STATUS current
			DESCRIPTION
				"Get the CPU silk-screen."
			::= { blade1CPUEntry 2 }
		
		b1CPUInfo OBJECT-TYPE
			SYNTAX DisplayString
			MAX-ACCESS read-only
			STATUS current
			DESCRIPTION
				"Get the CPU description of vendor, type and frequency."
			::= { blade1CPUEntry 3 }
		
		b1CPUPresent OBJECT-TYPE
			SYNTAX INTEGER
			MAX-ACCESS read-only
			STATUS current
			DESCRIPTION
				"Get the CPU presence status."
			::= { blade1CPUEntry 4 }
		
		b1CPUHealth OBJECT-TYPE
			SYNTAX INTEGER
			MAX-ACCESS read-only
			STATUS current
			DESCRIPTION
				"Get the CPU health status."
			::= { blade1CPUEntry 5 }
		
		b1CPULocation OBJECT-TYPE
			SYNTAX DisplayString
			MAX-ACCESS read-only
			STATUS current
			DESCRIPTION
				"Get the CPU location."
			::= { blade1CPUEntry 6 }
		
		blade1MemoryTable OBJECT-TYPE
			SYNTAX SEQUENCE OF Blade1MemoryEntry
			MAX-ACCESS not-accessible
			STATUS current
			DESCRIPTION
				"A table containing the list of Blade1 FRU information."
			::= { blade1 2007 }
		
		blade1MemoryEntry OBJECT-TYPE
			SYNTAX Blade1MemoryEntry
			MAX-ACCESS not-accessible
			STATUS current
			DESCRIPTION
				"Information about a particular current FRU."
			INDEX { b1MEMIndex }
			::= { blade1MemoryTable 1 }
		
		Blade1MemoryEntry ::=
			SEQUENCE { 
				b1MEMIndex
					INTEGER,
				b1MEMMark
					DisplayString,
				b1MEMInfo
					DisplayString,
				b1MEMPresent
					INTEGER,
				b1MEMHealth
					INTEGER,
				b1MEMLocation
					DisplayString
			 }

		b1MEMIndex OBJECT-TYPE
			SYNTAX INTEGER
			MAX-ACCESS not-accessible
			STATUS current
			DESCRIPTION
				"MEMORY INDEX"
			::= { blade1MemoryEntry 1 }
		
		b1MEMMark OBJECT-TYPE
			SYNTAX DisplayString
			MAX-ACCESS read-only
			STATUS current
			DESCRIPTION
				"Get the memory silk-screen."
			::= { blade1MemoryEntry 2 }
		
		b1MEMInfo OBJECT-TYPE
			SYNTAX DisplayString
			MAX-ACCESS read-only
			STATUS current
			DESCRIPTION
				"Get the memory description of vendor, frequency and capacity."
			::= { blade1MemoryEntry 3 }
		
		b1MEMPresent OBJECT-TYPE
			SYNTAX INTEGER
			MAX-ACCESS read-only
			STATUS current
			DESCRIPTION
				"Get the memory presence status."
			::= { blade1MemoryEntry 4 }
		
		b1MEMHealth OBJECT-TYPE
			SYNTAX INTEGER
			MAX-ACCESS read-only
			STATUS current
			DESCRIPTION
				"Get the memory health status."
			::= { blade1MemoryEntry 5 }
		
		b1MEMLocation OBJECT-TYPE
			SYNTAX DisplayString
			MAX-ACCESS read-only
			STATUS current
			DESCRIPTION
				"Get the memory location."
			::= { blade1MemoryEntry 6 }
		
		blade1MezzTable OBJECT-TYPE
			SYNTAX SEQUENCE OF Blade1MezzEntry
			MAX-ACCESS not-accessible
			STATUS current
			DESCRIPTION
				"A table containing the list of Blade1 FRU information."
			::= { blade1 2008 }
		
		blade1MezzEntry OBJECT-TYPE
			SYNTAX Blade1MezzEntry
			MAX-ACCESS not-accessible
			STATUS current
			DESCRIPTION
				"Information about a particular current FRU."
			INDEX { b1MezzIndex }
			::= { blade1MezzTable 1 }
		
		Blade1MezzEntry ::=
			SEQUENCE { 
				b1MezzIndex
					INTEGER,
				b1MezzMark
					DisplayString,
				b1MezzInfo
					DisplayString,
				b1MezzPresent
					INTEGER,
				b1MezzHealth
					INTEGER,
				b1MezzLocation
					DisplayString,
				b1MezzMac
					DisplayString
			 }

		b1MezzIndex OBJECT-TYPE
			SYNTAX INTEGER
			MAX-ACCESS not-accessible
			STATUS current
			DESCRIPTION
				"MEZZ INDEX"
			::= { blade1MezzEntry 1 }
		
		b1MezzMark OBJECT-TYPE
			SYNTAX DisplayString
			MAX-ACCESS read-only
			STATUS current
			DESCRIPTION
				"Get the MEZZ silk-screen."
			::= { blade1MezzEntry 2 }
		
		b1MezzInfo OBJECT-TYPE
			SYNTAX DisplayString
			MAX-ACCESS read-only
			STATUS current
			DESCRIPTION
				"Get the MEZZ description of type."
			::= { blade1MezzEntry 3 }
		
		b1MezzPresent OBJECT-TYPE
			SYNTAX INTEGER
			MAX-ACCESS read-only
			STATUS current
			DESCRIPTION
				"Get the MEZZ presence status."
			::= { blade1MezzEntry 4 }
		
		b1MezzHealth OBJECT-TYPE
			SYNTAX INTEGER
			MAX-ACCESS read-only
			STATUS current
			DESCRIPTION
				"Get the MEZZ health status."
			::= { blade1MezzEntry 5 }
		
		b1MezzLocation OBJECT-TYPE
			SYNTAX DisplayString
			MAX-ACCESS read-only
			STATUS current
			DESCRIPTION
				"Get the MEZZ location."
			::= { blade1MezzEntry 6 }
		
		b1MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade1MezzEntry 7 }
		
		blade1DiskTable OBJECT-TYPE
			SYNTAX SEQUENCE OF Blade1DiskEntry
			MAX-ACCESS not-accessible
			STATUS current
			DESCRIPTION
				"A table containing the list of Blade1 FRU information."
			::= { blade1 2009 }
		
		blade1DiskEntry OBJECT-TYPE
			SYNTAX Blade1DiskEntry
			MAX-ACCESS not-accessible
			STATUS current
			DESCRIPTION
				"Information about a particular current FRU."
			INDEX { b1DiskIndex }
			::= { blade1DiskTable 1 }
		
		Blade1DiskEntry ::=
			SEQUENCE { 
				b1DiskIndex
					INTEGER,
				b1DiskMark
					DisplayString,
				b1DiskInfo
					DisplayString,
				b1DiskPresent
					INTEGER,
				b1DiskHealth
					INTEGER,
				b1DiskLocation
					DisplayString
			 }

		b1DiskIndex OBJECT-TYPE
			SYNTAX INTEGER
			MAX-ACCESS not-accessible
			STATUS current
			DESCRIPTION
				"DISK INDEX"
			::= { blade1DiskEntry 1 }
		
		b1DiskMark OBJECT-TYPE
			SYNTAX DisplayString
			MAX-ACCESS read-only
			STATUS current
			DESCRIPTION
				"Get the disk silk-screen."
			::= { blade1DiskEntry 2 }
		
		b1DiskInfo OBJECT-TYPE
			SYNTAX DisplayString
			MAX-ACCESS read-only
			STATUS current
			DESCRIPTION
				"Get the disk description of vendor, capacity and speed."
			::= { blade1DiskEntry 3 }
		
		b1DiskPresent OBJECT-TYPE
			SYNTAX INTEGER
			MAX-ACCESS read-only
			STATUS current
			DESCRIPTION
				"Get the disk presence status."
			::= { blade1DiskEntry 4 }
		
		b1DiskHealth OBJECT-TYPE
			SYNTAX INTEGER
			MAX-ACCESS read-only
			STATUS current
			DESCRIPTION
				"Get the disk health status."
			::= { blade1DiskEntry 5 }
		
		b1DiskLocation OBJECT-TYPE
			SYNTAX DisplayString
			MAX-ACCESS read-only
			STATUS current
			DESCRIPTION
				"Get the disk location."
			::= { blade1DiskEntry 6 }
		
		blade1SecretKvmVmmTable OBJECT-TYPE
			SYNTAX SEQUENCE OF Blade1SecretKvmVmmEntry
			MAX-ACCESS not-accessible
			STATUS current
			DESCRIPTION
				"A table containing the list of Blade1 KVM&VMM secret information."
			::= { blade1 2010 }
		blade1SecretKvmVmmEntry OBJECT-TYPE
			SYNTAX Blade1SecretKvmVmmEntry
			MAX-ACCESS not-accessible
			STATUS current
			DESCRIPTION
				"Information about a particular current KVM&VMM."
			INDEX { b1SecretKvmVmmIndex }
			::= { blade1SecretKvmVmmTable 1 }
		Blade1SecretKvmVmmEntry ::=
			SEQUENCE { 
				b1SecretKvmVmmIndex
					INTEGER,
				b1SecretKvmState
					INTEGER,
				b1SecretVmmState
					INTEGER,
				b1MMSecretVmmKey
					DisplayString,
				b1SecretVmmKey
					DisplayString
			 }
		b1SecretKvmVmmIndex OBJECT-TYPE
			SYNTAX INTEGER
			MAX-ACCESS not-accessible
			STATUS current
			DESCRIPTION
				"KVM&VMM INDEX."
			::= { blade1SecretKvmVmmEntry 1 }
		b1SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade1SecretKvmVmmEntry 2 }
		b1SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade1SecretKvmVmmEntry 3 }
		b1MMSecretVmmKey OBJECT-TYPE
			SYNTAX DisplayString
			MAX-ACCESS read-only
			STATUS current
			DESCRIPTION
				"Get the MM secret VMM key."
			::= { blade1SecretKvmVmmEntry 4 }
		b1SecretVmmKey OBJECT-TYPE
			SYNTAX DisplayString
			MAX-ACCESS read-write
			STATUS current
			DESCRIPTION
				"Set the secret VMM key."
			::= { blade1SecretKvmVmmEntry 5 }
 		blade2 OBJECT IDENTIFIER ::= { blades 2 }
		
		
 		b2DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade2 4 }
		
 		b2PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade2 5 }
		
 		b2Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade2 6 }

		
 		b2Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b2Health information about a particular b2Location. 
				This will be one of the following:
				(0-ok, 1-minor, 2-major, 3-majorandminor,4-critical,5-criticalandminor,6-criticalandmajor,7-criticalandmajorandminor)"
			::= { blade2 8 }
		
 		b2HealthEvents OBJECT-TYPE
			SYNTAX DisplayString
			MAX-ACCESS read-only
			STATUS current
			DESCRIPTION
				"Events that contribute to the b2Health of the b2Location.  
				This is a list of events currently happening on the 
				b2Location."
			::= { blade2 9 }
		
 		b2ClearSEL OBJECT-TYPE
			SYNTAX INTEGER { clear(1) }
			MAX-ACCESS read-write
			STATUS current
			DESCRIPTION
				"Clean the BMC's SEL on the board."
			::= { blade2 12 }
		
 		b2ExDiskBoardPresence OBJECT-TYPE
			SYNTAX INTEGER
				{
				not-present(0),
				present(1)
				}
			MAX-ACCESS read-only
			STATUS current
			DESCRIPTION
				"Used to find out if the extended disk board is present.
				0 - not present
				1 - present"
			::= { blade2 14 }
		
 		b2BladeVersion OBJECT-TYPE
			SYNTAX DisplayString
			MAX-ACCESS read-only
			STATUS current
			DESCRIPTION
				"display the Version of board2."
			::= { blade2 20 }
		
 		b2MACAddress OBJECT-TYPE
			SYNTAX DisplayString
			MAX-ACCESS read-only
			STATUS current
			DESCRIPTION
				"display the MACAddress of board2."
			::= { blade2 21 }
		
				
							
		
 		b2Safepwofftime OBJECT-TYPE
			SYNTAX INTEGER
			MAX-ACCESS read-write
			STATUS current
			DESCRIPTION
				"the safe poweroff time.
				"
			::= { blade2 26 }
		
 		b2BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade2 32 }
		
 		b2Systeminfo OBJECT-TYPE
			SYNTAX DisplayString
			MAX-ACCESS read-write
			STATUS current
			DESCRIPTION
				"display the system information of board2."
			::= { blade2 36 }

		
 		b2SystemProperties OBJECT-TYPE
			SYNTAX DisplayString
			MAX-ACCESS read-only
			STATUS current
			DESCRIPTION
				"Get the power of blade1."
			::= { blade2 39 }
		
 		b2BiosCfg OBJECT-TYPE
			SYNTAX DisplayString
			MAX-ACCESS read-write
			STATUS current
			DESCRIPTION
				"Get the power of blade1."
			::= { blade2 40 }
		
 		b2WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade2 41 }
		
 		b2RealTimePower OBJECT-TYPE
			SYNTAX INTEGER
			MAX-ACCESS read-only
			STATUS current
			DESCRIPTION
				" "
			::= { blade2 43 }
		
 		b2PowerCapping OBJECT-TYPE
			SYNTAX DisplayString
			MAX-ACCESS read-write
			STATUS current
			DESCRIPTION
				" "
			::= { blade2 44 }
		
 		b2Powerreference OBJECT-TYPE
			SYNTAX INTEGER
			MAX-ACCESS read-only
			STATUS current
			DESCRIPTION
				" "
			::= { blade2 45 }
		
 		b2ClearBiosConfig OBJECT-TYPE
			SYNTAX INTEGER
			MAX-ACCESS read-write
			STATUS current
			DESCRIPTION
				" "
			::= { blade2 46 }
		
 		b2BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade2 47 }
		
 		b2BmcUserAdd OBJECT-TYPE
			SYNTAX DisplayString
			MAX-ACCESS read-write
			STATUS current
			DESCRIPTION
				"Used to Add the BMC User
				settable format:
				username,passwd"
			::= { blade2 48 }
		
 		b2BmcUserDel OBJECT-TYPE
			SYNTAX DisplayString
			MAX-ACCESS read-write
			STATUS current
			DESCRIPTION
				"Used to Del the BMC User
				settable format:
				username"
			::= { blade2 49 }
		
 		b2BmcUserPasswd OBJECT-TYPE
			SYNTAX DisplayString
			MAX-ACCESS read-write
			STATUS current
			DESCRIPTION
				"Used to Change the BMC User Passwd
				settable format:
				username,passwd"
			::= { blade2 50 }
		
 		b2BmcUserpropertychg OBJECT-TYPE
			SYNTAX DisplayString
			MAX-ACCESS read-write
			STATUS current
			DESCRIPTION
				"Used to Change the BMC User Property
				settable format:
				username,property"
			::= { blade2 51 }
		
 		b2BmcGateway OBJECT-TYPE
			SYNTAX DisplayString
			MAX-ACCESS read-write
			STATUS current
			DESCRIPTION
				"Read or set the gateway."
			::= { blade2 52 }
		
 		b2SlotBitmap OBJECT-TYPE
			SYNTAX INTEGER
			MAX-ACCESS read-only
			STATUS current
			DESCRIPTION
				" "
			::= { blade2 55 }
		
		b2systemGuid OBJECT-TYPE
			SYNTAX DisplayString
			MAX-ACCESS read-only
			STATUS current
			DESCRIPTION
				" "
			::= { blade2 56 }
		
		b2ProductName OBJECT-TYPE
			SYNTAX DisplayString
			MAX-ACCESS read-only
			STATUS current
			DESCRIPTION
				"display the Version of board2."
			::= { blade2 57 }

		b2BundleVersion OBJECT-TYPE
			SYNTAX DisplayString
			MAX-ACCESS read-write
			STATUS current
			DESCRIPTION
				"Get or set the board2 bundle version."
			::= { blade2 58 }

 		blade2SensorTargetTable OBJECT-TYPE
			SYNTAX SEQUENCE OF Blade2SensorTargetEntry
			MAX-ACCESS not-accessible
			STATUS current
			DESCRIPTION
				"A table containing the list of sensor information."
			::= { blade2 2001 }
		
 		blade2SensorTargetEntry OBJECT-TYPE
			SYNTAX Blade2SensorTargetEntry
			MAX-ACCESS not-accessible
			STATUS current
			DESCRIPTION
				"Information about a particular current sensor."
			INDEX { b2Target }
			::= { blade2SensorTargetTable 1 }
		
		Blade2SensorTargetEntry ::=
			SEQUENCE { 
				b2Target
					DisplayString,
				b2Current
					DisplayString,
				b2ThresholdsAll
					DisplayString,
				b2UpperCritical
					DisplayString,
				b2UpperNonCritical
					DisplayString,
				b2UpperNonRecoverable
					DisplayString,
				b2LowerNonCritical
					DisplayString,
				b2LowerCritical
					DisplayString,
				b2LowerNonRecoverable
					DisplayString,
				b2SensorHealth
					INTEGER,
				b2SensorHealthEvents
					DisplayString,
				b2NegativeHysteresis
					DisplayString,
				b2PositiveHysteresis
					DisplayString,
				b2SensorType
					DisplayString,
				b2SensorFRUInfo
					DisplayString
			 }

 		b2Target OBJECT-TYPE
			SYNTAX DisplayString
			MAX-ACCESS not-accessible
			STATUS current
			DESCRIPTION
				"sensor Name"
			::= { blade2SensorTargetEntry 1 }
		
 		b2Current OBJECT-TYPE
			SYNTAX DisplayString
			MAX-ACCESS read-only
			STATUS current
			DESCRIPTION
				"Display the current value of a sensor."
			::= { blade2SensorTargetEntry 2 }
		
 		b2ThresholdsAll OBJECT-TYPE
			SYNTAX DisplayString
			MAX-ACCESS read-only
			STATUS current
			DESCRIPTION
				"All thresholds of a sensor"
			::= { blade2SensorTargetEntry 3 }
		
 		b2UpperCritical OBJECT-TYPE
			SYNTAX DisplayString
			MAX-ACCESS read-write
			STATUS current
			DESCRIPTION
				"Upper critical thresholds"
			::= { blade2SensorTargetEntry 4 }
		
 		b2UpperNonCritical OBJECT-TYPE
			SYNTAX DisplayString
			MAX-ACCESS read-write
			STATUS current
			DESCRIPTION
				"Upper non-critical thresholds"
			::= { blade2SensorTargetEntry 5 }
		
 		b2UpperNonRecoverable OBJECT-TYPE
			SYNTAX DisplayString
			MAX-ACCESS read-write
			STATUS current
			DESCRIPTION
				"Upper non-recoverable thresholds"
			::= { blade2SensorTargetEntry 6 }
		
 		b2LowerNonCritical OBJECT-TYPE
			SYNTAX DisplayString
			MAX-ACCESS read-write
			STATUS current
			DESCRIPTION
				"Lower non-critical thresholds"
			::= { blade2SensorTargetEntry 7 }
		
 		b2LowerCritical OBJECT-TYPE
			SYNTAX DisplayString
			MAX-ACCESS read-write
			STATUS current
			DESCRIPTION
				"Lower critical thresholds"
			::= { blade2SensorTargetEntry 8 }
		
 		b2LowerNonRecoverable OBJECT-TYPE
			SYNTAX DisplayString
			MAX-ACCESS read-write
			STATUS current
			DESCRIPTION
				"Lower non-recoverable thresholds"
			::= { blade2SensorTargetEntry 9 }
		
 		b2SensorHealth OBJECT-TYPE
			SYNTAX INTEGER
				{
				ok(0),
				minor(1),
				major(2),
				critical(3)
				}
			MAX-ACCESS read-only
			STATUS current
			DESCRIPTION
				"b2Health information about a particular b2Location. 
				This will be one of the following:
				(0-ok, 1-minor, 2-major, 3-critical)"
			::= { blade2SensorTargetEntry 10 }
		
 		b2SensorHealthEvents OBJECT-TYPE
			SYNTAX DisplayString
			MAX-ACCESS read-only
			STATUS current
			DESCRIPTION
				"Events that contribute to the b2Health of the b2Location.  
				This is a list of events currently happening on the 
				b2Location."
			::= { blade2SensorTargetEntry 11 }
		
		
 		b2NegativeHysteresis OBJECT-TYPE
			SYNTAX DisplayString
			MAX-ACCESS read-write
			STATUS current
			DESCRIPTION
				"Get/Set the negativeHysteresis value."
			::= { blade2SensorTargetEntry 16 }
		
 		b2PositiveHysteresis OBJECT-TYPE
			SYNTAX DisplayString
			MAX-ACCESS read-write
			STATUS current
			DESCRIPTION
				"Get/Set the positiveHysteresis value."
			::= { blade2SensorTargetEntry 17 }
		
 		b2SensorType OBJECT-TYPE
			SYNTAX DisplayString
			MAX-ACCESS read-only
			STATUS current
			DESCRIPTION
				"Get the type of the sensor."
			::= { blade2SensorTargetEntry 18 }
		
 		b2SensorFRUInfo OBJECT-TYPE
			SYNTAX DisplayString
			MAX-ACCESS read-only
			STATUS current
			DESCRIPTION
				"Get the fruinfo of the sensor."
			::= { blade2SensorTargetEntry 19 }
		
 		blade2FruTable OBJECT-TYPE
			SYNTAX SEQUENCE OF Blade2FruEntry
			MAX-ACCESS not-accessible
			STATUS current
			DESCRIPTION
				"A table containing the list of FRU information."
			::= { blade2 2002 }
		
 		blade2FruEntry OBJECT-TYPE
			SYNTAX Blade2FruEntry
			MAX-ACCESS not-accessible
			STATUS current
			DESCRIPTION
				"Information about a particular current FRU."
			INDEX { b2fruNumber }
			::= { blade2FruTable 1 }
		
		Blade2FruEntry ::=
			SEQUENCE { 
				b2fruNumber
					INTEGER,
				b2FruHotSwapState
					DisplayString,
				b2FruLedProperties
					DisplayString,
				b2FRUControl
					INTEGER,
				b2FRULabel
					DisplayString,
				b2ResetReason
					DisplayString
			 }

 		b2fruNumber OBJECT-TYPE
			SYNTAX INTEGER
			MAX-ACCESS not-accessible
			STATUS current
			DESCRIPTION
				" "
			::= { blade2FruEntry 1 }
		
 		b2FruHotSwapState OBJECT-TYPE
			SYNTAX DisplayString
			MAX-ACCESS read-only
			STATUS current
			DESCRIPTION
				"Retrieve the hot swap state of the FRU from the 
				internally known hot swap states of blade2."
			::= { blade2FruEntry 3 }
		
 		b2FruLedProperties OBJECT-TYPE
			SYNTAX DisplayString
			MAX-ACCESS read-only
			STATUS current
			DESCRIPTION
				"Retrieves the LED support information from a FRU. Returns a comma separated
				list of LEDS and the number of FRU supported user LEDs."
			::= { blade2FruEntry 4 }

		

		b2FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade2FruEntry 9 }
		
 		b2FRULabel OBJECT-TYPE
			SYNTAX DisplayString
			MAX-ACCESS read-only
			STATUS current
			DESCRIPTION
				"Get fru label of blade2."
			::= { blade2FruEntry 10 }
		
 		b2ResetReason OBJECT-TYPE
			SYNTAX DisplayString
			MAX-ACCESS read-only
			STATUS current
			DESCRIPTION
				"Delete fru label of smm."
			::= { blade2FruEntry 11 }
		
 		blade2FruLedTable OBJECT-TYPE
			SYNTAX SEQUENCE OF Blade2FruLedEntry
			MAX-ACCESS not-accessible
			STATUS current
			DESCRIPTION
				"A table containing the list of led information."
			::= { blade2 2003 }
		
 		blade2FruLedEntry OBJECT-TYPE
			SYNTAX Blade2FruLedEntry
			MAX-ACCESS not-accessible
			STATUS current
			DESCRIPTION
				"Information about a particular current led."
			INDEX { b2FruID, b2FruLed }
			::= { blade2FruLedTable 1 }
		
		Blade2FruLedEntry ::=
			SEQUENCE { 
				b2FruID
					INTEGER,
				b2FruLed
					DisplayString,
				b2FruLedColorProps
					DisplayString,
				b2FruLedState
					DisplayString
			 }

 		b2FruID OBJECT-TYPE
			SYNTAX INTEGER
			MAX-ACCESS not-accessible
			STATUS current
			DESCRIPTION
				" "
			::= { blade2FruLedEntry 1 }
		
 		b2FruLed OBJECT-TYPE
			SYNTAX DisplayString
			MAX-ACCESS not-accessible
			STATUS current
			DESCRIPTION
				" "
			::= { blade2FruLedEntry 2 }
		
 		b2FruLedColorProps OBJECT-TYPE
			SYNTAX DisplayString
			MAX-ACCESS read-only
			STATUS current
			DESCRIPTION
				"Finds out what colors are supported by the LED"
			::= { blade2FruLedEntry 3 }
		
 		b2FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade2FruLedEntry 4 }
		
 		blade2FruDescriptionTable OBJECT-TYPE
			SYNTAX SEQUENCE OF Blade2FruDescriptionEntry
			MAX-ACCESS not-accessible
			STATUS current
			DESCRIPTION
				"A table containing the list of blade2 FRU information."
			::= { blade2 2004 }
		
 		blade2FruDescriptionEntry OBJECT-TYPE
			SYNTAX Blade2FruDescriptionEntry
			MAX-ACCESS not-accessible
			STATUS current
			DESCRIPTION
				"Information about a particular current FRU."
			INDEX { b2fruNum }
			::= { blade2FruDescriptionTable 1 }
		
		Blade2FruDescriptionEntry ::=
			SEQUENCE { 
				b2fruNum
					INTEGER,
				b2fruBoardDescription
					DisplayString,
				b2fruBoardManufacturer
					DisplayString,
				b2fruBoardPartNumber
					DisplayString,
				b2fruBoardSerialNumber
					DisplayString,
				b2fruBoardManufactureDate
					DisplayString,
				b2fruProductDescription
					DisplayString,
				b2fruProductManufacturer
					DisplayString,
				b2fruProductPartNumber
					DisplayString,
				b2fruProductSerialNumber
					DisplayString,
				b2fruProductRevision
					DisplayString,
				b2fruAll
					DisplayString
			 }

 		b2fruNum OBJECT-TYPE
			SYNTAX INTEGER
			MAX-ACCESS not-accessible
			STATUS current
			DESCRIPTION
				"blade2 FRU's INDEX"
			::= { blade2FruDescriptionEntry 1 }
		
 		b2fruBoardDescription OBJECT-TYPE
			SYNTAX DisplayString
			MAX-ACCESS read-only
			STATUS current
			DESCRIPTION
				"Used to read the Board Description from the blade2 fru."
			::= { blade2FruDescriptionEntry 2 }
		
 		b2fruBoardManufacturer OBJECT-TYPE
			SYNTAX DisplayString
			MAX-ACCESS read-only
			STATUS current
			DESCRIPTION
				"Used to read the Board Manufacturer from the blade2 fru."
			::= { blade2FruDescriptionEntry 3 }
		
 		b2fruBoardPartNumber OBJECT-TYPE
			SYNTAX DisplayString
			MAX-ACCESS read-only
			STATUS current
			DESCRIPTION
				"Used to read the Board Part Number from the blade2 fru."
			::= { blade2FruDescriptionEntry 4 }
		
 		b2fruBoardSerialNumber OBJECT-TYPE
			SYNTAX DisplayString
			MAX-ACCESS read-only
			STATUS current
			DESCRIPTION
				"Used to read the Board Serial Number from the blade2 fru."
			::= { blade2FruDescriptionEntry 5 }
		
 		b2fruBoardManufactureDate OBJECT-TYPE
			SYNTAX DisplayString
			MAX-ACCESS read-only
			STATUS current
			DESCRIPTION
				"Used to read the Board Manufacture Date from the blade2 fru."
			::= { blade2FruDescriptionEntry 6 }
		
 		b2fruProductDescription OBJECT-TYPE
			SYNTAX DisplayString
			MAX-ACCESS read-only
			STATUS current
			DESCRIPTION
				"Used to read the Product Description from the blade2 fru."
			::= { blade2FruDescriptionEntry 7 }
		
 		b2fruProductManufacturer OBJECT-TYPE
			SYNTAX DisplayString
			MAX-ACCESS read-only
			STATUS current
			DESCRIPTION
				"Used to read the Product Manufacturer from the blade2 fru."
			::= { blade2FruDescriptionEntry 8 }
		
 		b2fruProductPartNumber OBJECT-TYPE
			SYNTAX DisplayString
			MAX-ACCESS read-only
			STATUS current
			DESCRIPTION
				"Used to read the Product Part Number from the blade2 fru."
			::= { blade2FruDescriptionEntry 9 }
		
 		b2fruProductSerialNumber OBJECT-TYPE
			SYNTAX DisplayString
			MAX-ACCESS read-only
			STATUS current
			DESCRIPTION
				"Used to read the Product Serial Number from the blade2 fru."
			::= { blade2FruDescriptionEntry 10 }
		
 		b2fruProductRevision OBJECT-TYPE
			SYNTAX DisplayString
			MAX-ACCESS read-only
			STATUS current
			DESCRIPTION
				"Used to read the Product Revision from the blade2 fru."
			::= { blade2FruDescriptionEntry 13 }
		
 		b2fruAll OBJECT-TYPE
			SYNTAX DisplayString
			MAX-ACCESS read-only
			STATUS current
			DESCRIPTION
				"Used to read the fru info all."
			::= { blade2FruDescriptionEntry 14 }
		
		blade2CPUTable OBJECT-TYPE
			SYNTAX SEQUENCE OF Blade2CPUEntry
			MAX-ACCESS not-accessible
			STATUS current
			DESCRIPTION
				"A table containing the list of Blade1 FRU information."
			::= { blade2 2006 }
		
		blade2CPUEntry OBJECT-TYPE
			SYNTAX Blade2CPUEntry
			MAX-ACCESS not-accessible
			STATUS current
			DESCRIPTION
				"Information about a particular current FRU."
			INDEX { b2CPUIndex }
			::= { blade2CPUTable 1 }
		
		Blade2CPUEntry ::=
			SEQUENCE { 
				b2CPUIndex
					INTEGER,
				b2CPUMark
					DisplayString,
				b2CPUInfo
					DisplayString,
				b2CPUPresent
					INTEGER,
				b2CPUHealth
					INTEGER,
				b2CPULocation
					DisplayString
			 }

		b2CPUIndex OBJECT-TYPE
			SYNTAX INTEGER
			MAX-ACCESS not-accessible
			STATUS current
			DESCRIPTION
				"CPU INDEX"
			::= { blade2CPUEntry 1 }
		
		b2CPUMark OBJECT-TYPE
			SYNTAX DisplayString
			MAX-ACCESS read-only
			STATUS current
			DESCRIPTION
				"Get the CPU silk-screen."
			::= { blade2CPUEntry 2 }
		
		b2CPUInfo OBJECT-TYPE
			SYNTAX DisplayString
			MAX-ACCESS read-only
			STATUS current
			DESCRIPTION
				"Get the CPU description of vendor, type and frequency."
			::= { blade2CPUEntry 3 }
		
		b2CPUPresent OBJECT-TYPE
			SYNTAX INTEGER
			MAX-ACCESS read-only
			STATUS current
			DESCRIPTION
				"Get the CPU presence status."
			::= { blade2CPUEntry 4 }
		
		b2CPUHealth OBJECT-TYPE
			SYNTAX INTEGER
			MAX-ACCESS read-only
			STATUS current
			DESCRIPTION
				"Get the CPU health status."
			::= { blade2CPUEntry 5 }
		
		b2CPULocation OBJECT-TYPE
			SYNTAX DisplayString
			MAX-ACCESS read-only
			STATUS current
			DESCRIPTION
				"Get the CPU location."
			::= { blade2CPUEntry 6 }
		
		blade2MemoryTable OBJECT-TYPE
			SYNTAX SEQUENCE OF Blade2MemoryEntry
			MAX-ACCESS not-accessible
			STATUS current
			DESCRIPTION
				"A table containing the list of Blade1 FRU information."
			::= { blade2 2007 }
		
		blade2MemoryEntry OBJECT-TYPE
			SYNTAX Blade2MemoryEntry
			MAX-ACCESS not-accessible
			STATUS current
			DESCRIPTION
				"Information about a particular current FRU."
			INDEX { b2MEMIndex }
			::= { blade2MemoryTable 1 }
		
		Blade2MemoryEntry ::=
			SEQUENCE { 
				b2MEMIndex
					INTEGER,
				b2MEMMark
					DisplayString,
				b2MEMInfo
					DisplayString,
				b2MEMPresent
					INTEGER,
				b2MEMHealth
					INTEGER,
				b2MEMLocation
					DisplayString
			 }

		b2MEMIndex OBJECT-TYPE
			SYNTAX INTEGER
			MAX-ACCESS not-accessible
			STATUS current
			DESCRIPTION
				"MEMORY INDEX"
			::= { blade2MemoryEntry 1 }
		
		b2MEMMark OBJECT-TYPE
			SYNTAX DisplayString
			MAX-ACCESS read-only
			STATUS current
			DESCRIPTION
				"Get the memory silk-screen."
			::= { blade2MemoryEntry 2 }
		
		b2MEMInfo OBJECT-TYPE
			SYNTAX DisplayString
			MAX-ACCESS read-only
			STATUS current
			DESCRIPTION
				"Get the memory description of vendor, frequency and capacity."
			::= { blade2MemoryEntry 3 }
		
		b2MEMPresent OBJECT-TYPE
			SYNTAX INTEGER
			MAX-ACCESS read-only
			STATUS current
			DESCRIPTION
				"Get the memory presence status."
			::= { blade2MemoryEntry 4 }
		
		b2MEMHealth OBJECT-TYPE
			SYNTAX INTEGER
			MAX-ACCESS read-only
			STATUS current
			DESCRIPTION
				"Get the memory health status."
			::= { blade2MemoryEntry 5 }
		
		b2MEMLocation OBJECT-TYPE
			SYNTAX DisplayString
			MAX-ACCESS read-only
			STATUS current
			DESCRIPTION
				"Get the memory location."
			::= { blade2MemoryEntry 6 }
		
		blade2MezzTable OBJECT-TYPE
			SYNTAX SEQUENCE OF Blade2MezzEntry
			MAX-ACCESS not-accessible
			STATUS current
			DESCRIPTION
				"A table containing the list of Blade1 FRU information."
			::= { blade2 2008 }
		
		blade2MezzEntry OBJECT-TYPE
			SYNTAX Blade2MezzEntry
			MAX-ACCESS not-accessible
			STATUS current
			DESCRIPTION
				"Information about a particular current FRU."
			INDEX { b2MezzIndex }
			::= { blade2MezzTable 1 }
		
		Blade2MezzEntry ::=
			SEQUENCE { 
				b2MezzIndex
					INTEGER,
				b2MezzMark
					DisplayString,
				b2MezzInfo
					DisplayString,
				b2MezzPresent
					INTEGER,
				b2MezzHealth
					INTEGER,
				b2MezzLocation
					DisplayString,
				b2MezzMac
					DisplayString
			 }

		b2MezzIndex OBJECT-TYPE
			SYNTAX INTEGER
			MAX-ACCESS not-accessible
			STATUS current
			DESCRIPTION
				"MEZZ INDEX"
			::= { blade2MezzEntry 1 }
		
		b2MezzMark OBJECT-TYPE
			SYNTAX DisplayString
			MAX-ACCESS read-only
			STATUS current
			DESCRIPTION
				"Get the MEZZ silk-screen."
			::= { blade2MezzEntry 2 }
		
		b2MezzInfo OBJECT-TYPE
			SYNTAX DisplayString
			MAX-ACCESS read-only
			STATUS current
			DESCRIPTION
				"Get the MEZZ description of type."
			::= { blade2MezzEntry 3 }
		
		b2MezzPresent OBJECT-TYPE
			SYNTAX INTEGER
			MAX-ACCESS read-only
			STATUS current
			DESCRIPTION
				"Get the MEZZ presence status."
			::= { blade2MezzEntry 4 }
		
		b2MezzHealth OBJECT-TYPE
			SYNTAX INTEGER
			MAX-ACCESS read-only
			STATUS current
			DESCRIPTION
				"Get the MEZZ health status."
			::= { blade2MezzEntry 5 }
		
		b2MezzLocation OBJECT-TYPE
			SYNTAX DisplayString
			MAX-ACCESS read-only
			STATUS current
			DESCRIPTION
				"Get the MEZZ location."
			::= { blade2MezzEntry 6 }
		
		b2MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade2MezzEntry 7 }
		
		blade2DiskTable OBJECT-TYPE
			SYNTAX SEQUENCE OF Blade2DiskEntry
			MAX-ACCESS not-accessible
			STATUS current
			DESCRIPTION
				"A table containing the list of Blade1 FRU information."
			::= { blade2 2009 }
		
		blade2DiskEntry OBJECT-TYPE
			SYNTAX Blade2DiskEntry
			MAX-ACCESS not-accessible
			STATUS current
			DESCRIPTION
				"Information about a particular current FRU."
			INDEX { b2DiskIndex }
			::= { blade2DiskTable 1 }
		
		Blade2DiskEntry ::=
			SEQUENCE { 
				b2DiskIndex
					INTEGER,
				b2DiskMark
					DisplayString,
				b2DiskInfo
					DisplayString,
				b2DiskPresent
					INTEGER,
				b2DiskHealth
					INTEGER,
				b2DiskLocation
					DisplayString
			 }

		b2DiskIndex OBJECT-TYPE
			SYNTAX INTEGER
			MAX-ACCESS not-accessible
			STATUS current
			DESCRIPTION
				"DISK INDEX"
			::= { blade2DiskEntry 1 }
		
		b2DiskMark OBJECT-TYPE
			SYNTAX DisplayString
			MAX-ACCESS read-only
			STATUS current
			DESCRIPTION
				"Get the disk silk-screen."
			::= { blade2DiskEntry 2 }
		
		b2DiskInfo OBJECT-TYPE
			SYNTAX DisplayString
			MAX-ACCESS read-only
			STATUS current
			DESCRIPTION
				"Get the disk description of vendor, capacity and speed."
			::= { blade2DiskEntry 3 }
		
		b2DiskPresent OBJECT-TYPE
			SYNTAX INTEGER
			MAX-ACCESS read-only
			STATUS current
			DESCRIPTION
				"Get the disk presence status."
			::= { blade2DiskEntry 4 }
		
		b2DiskHealth OBJECT-TYPE
			SYNTAX INTEGER
			MAX-ACCESS read-only
			STATUS current
			DESCRIPTION
				"Get the disk health status."
			::= { blade2DiskEntry 5 }
		
		b2DiskLocation OBJECT-TYPE
			SYNTAX DisplayString
			MAX-ACCESS read-only
			STATUS current
			DESCRIPTION
				"Get the disk location."
			::= { blade2DiskEntry 6 }
		
		blade2SecretKvmVmmTable OBJECT-TYPE
			SYNTAX SEQUENCE OF Blade2SecretKvmVmmEntry
			MAX-ACCESS not-accessible
			STATUS current
			DESCRIPTION
				"A table containing the list of Blade2 KVM&VMM secret information."
			::= { blade2 2010 }

		blade2SecretKvmVmmEntry OBJECT-TYPE
			SYNTAX Blade2SecretKvmVmmEntry
			MAX-ACCESS not-accessible
			STATUS current
			DESCRIPTION
				"Information about a particular current KVM&VMM."
			INDEX { b2SecretKvmVmmIndex }
			::= { blade2SecretKvmVmmTable 1 }
		Blade2SecretKvmVmmEntry ::=
			SEQUENCE { 
				b2SecretKvmVmmIndex
					INTEGER,
				b2SecretKvmState
					INTEGER,
				b2SecretVmmState
					INTEGER,
				b2MMSecretVmmKey
					DisplayString,
				b2SecretVmmKey
					DisplayString
			 }
		b2SecretKvmVmmIndex OBJECT-TYPE
			SYNTAX INTEGER
			MAX-ACCESS not-accessible
			STATUS current
			DESCRIPTION
				"KVM&VMM INDEX."
			::= { blade2SecretKvmVmmEntry 1 }
		b2SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade2SecretKvmVmmEntry 2 }
		b2SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade2SecretKvmVmmEntry 3 }
		b2MMSecretVmmKey OBJECT-TYPE
			SYNTAX DisplayString
			MAX-ACCESS read-only
			STATUS current
			DESCRIPTION
				"Get the MM secret VMM key."
			::= { blade2SecretKvmVmmEntry 4 }
		b2SecretVmmKey OBJECT-TYPE
			SYNTAX DisplayString
			MAX-ACCESS read-write
			STATUS current
			DESCRIPTION
				"Set the secret VMM key."
			::= { blade2SecretKvmVmmEntry 5 }
		blade3 OBJECT IDENTIFIER ::= { blades 3 }

		
 		b3DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade3 4 }
		
 		b3PowerState OBJECT-TYPE
			SYNTAX DisplayString
			MAX-ACCESS read-write
			STATUS current
			DESCRIPTION
				"The power state of a blade.  This is used to find out 
				if a blade is present, healthy, on/off , to shutdown and turn on 
				a blade.   
				poweron - Power on a blade
				poweroff - Power off a blade"
			::= { blade3 5 }
		
 		b3Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade3 6 }

		
 		b3Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b3Health information about a particular b3Location. 
				This will be one of the following:
					(0-ok, 1-minor, 2-major, 3-majorandminor,4-critical,5-criticalandminor,6-criticalandmajor,7-criticalandmajorandminor)"
			::= { blade3 8 }
		
 		b3HealthEvents OBJECT-TYPE
			SYNTAX DisplayString
			MAX-ACCESS read-only
			STATUS current
			DESCRIPTION
				"Events that contribute to the b3Health of the b3Location.  
				This is a list of events currently happening on the 
				b3Location."
			::= { blade3 9 }
		
 		b3ClearSEL OBJECT-TYPE
			SYNTAX INTEGER { clear(1) }
			MAX-ACCESS read-write
			STATUS current
			DESCRIPTION
				"Clean the BMC's SEL on the board."
			::= { blade3 12 }
		
 		b3ExDiskBoardPresence OBJECT-TYPE
			SYNTAX INTEGER
				{
				not-present(0),
				present(1)
				}
			MAX-ACCESS read-only
			STATUS current
			DESCRIPTION
				"Used to find out if the extended disk board is present.
				0 - not present
				1 - present"
			::= { blade3 14 }
		
 		b3BladeVersion OBJECT-TYPE
			SYNTAX DisplayString
			MAX-ACCESS read-only
			STATUS current
			DESCRIPTION
				"display the Version of board3."
			::= { blade3 20 }
		
 		b3MACAddress OBJECT-TYPE
			SYNTAX DisplayString
			MAX-ACCESS read-only
			STATUS current
			DESCRIPTION
				"display the MACAddress of board3."
			::= { blade3 21 }
		
				
							
		
 		b3Safepwofftime OBJECT-TYPE
			SYNTAX INTEGER
			MAX-ACCESS read-write
			STATUS current
			DESCRIPTION
				"the safe poweroff time.
				"
			::= { blade3 26 }
		
 		b3BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2] 
				6=Force boot into BIOS Setup
				15=Force boot from Floppy/primary removable media           
				
				"
			::= { blade3 32 }
		
 		b3Systeminfo OBJECT-TYPE
			SYNTAX DisplayString
			MAX-ACCESS read-write
			STATUS current
			DESCRIPTION
				"display the system information of board3."
			::= { blade3 36 }

		
 		b3SystemProperties OBJECT-TYPE
			SYNTAX DisplayString
			MAX-ACCESS read-only
			STATUS current
			DESCRIPTION
				"Get the power of blade1."
			::= { blade3 39 }
		
 		b3BiosCfg OBJECT-TYPE
			SYNTAX DisplayString
			MAX-ACCESS read-write
			STATUS current
			DESCRIPTION
				"Get the power of blade1."
			::= { blade3 40 }
		
 		b3WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade3 41 }
		
 		b3RealTimePower OBJECT-TYPE
			SYNTAX INTEGER
			MAX-ACCESS read-only
			STATUS current
			DESCRIPTION
				" "
			::= { blade3 43 }
		
 		b3PowerCapping OBJECT-TYPE
			SYNTAX DisplayString
			MAX-ACCESS read-write
			STATUS current
			DESCRIPTION
				" "
			::= { blade3 44 }
		
 		b3Powerreference OBJECT-TYPE
			SYNTAX INTEGER
			MAX-ACCESS read-only
			STATUS current
			DESCRIPTION
				" "
			::= { blade3 45 }
		
 		b3ClearBiosConfig OBJECT-TYPE
			SYNTAX INTEGER
			MAX-ACCESS read-write
			STATUS current
			DESCRIPTION
				" "
			::= { blade3 46 }
		
 		b3BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade3 47 }
		
 		b3BmcUserAdd OBJECT-TYPE
			SYNTAX DisplayString
			MAX-ACCESS read-write
			STATUS current
			DESCRIPTION
				"Used to Add the BMC User
				settable format:
				username,passwd"
			::= { blade3 48 }
		
 		b3BmcUserDel OBJECT-TYPE
			SYNTAX DisplayString
			MAX-ACCESS read-write
			STATUS current
			DESCRIPTION
				"Used to Del the BMC User
				settable format:
				username"
			::= { blade3 49 }
		
 		b3BmcUserPasswd OBJECT-TYPE
			SYNTAX DisplayString
			MAX-ACCESS read-write
			STATUS current
			DESCRIPTION
				"Used to Change the BMC User Passwd
				settable format:
				username,passwd"
			::= { blade3 50 }
		
 		b3BmcUserpropertychg OBJECT-TYPE
			SYNTAX DisplayString
			MAX-ACCESS read-write
			STATUS current
			DESCRIPTION
				"Used to Change the BMC User Property
				settable format:
				username,property"
			::= { blade3 51 }
		
 		b3BmcGateway OBJECT-TYPE
			SYNTAX DisplayString
			MAX-ACCESS read-write
			STATUS current
			DESCRIPTION
				"Read or set the gateway."
			::= { blade3 52 }
		
 		b3SlotBitmap OBJECT-TYPE
			SYNTAX INTEGER
			MAX-ACCESS read-only
			STATUS current
			DESCRIPTION
				" "
			::= { blade3 55 }
		
		b3systemGuid OBJECT-TYPE
			SYNTAX DisplayString
			MAX-ACCESS read-only
			STATUS current
			DESCRIPTION
				" "
			::= { blade3 56 }
		
		b3ProductName OBJECT-TYPE
			SYNTAX DisplayString
			MAX-ACCESS read-only
			STATUS current
			DESCRIPTION
				"display the Version of board3."
			::= { blade3 57 }

		b3BundleVersion OBJECT-TYPE
			SYNTAX DisplayString
			MAX-ACCESS read-write
			STATUS current
			DESCRIPTION
				"Get or set the board3 bundle version."
			::= { blade3 58 }

 		blade3SensorTargetTable OBJECT-TYPE
			SYNTAX SEQUENCE OF Blade3SensorTargetEntry
			MAX-ACCESS not-accessible
			STATUS current
			DESCRIPTION
				"A table containing the list of sensor information."
			::= { blade3 2001 }
		
 		blade3SensorTargetEntry OBJECT-TYPE
			SYNTAX Blade3SensorTargetEntry
			MAX-ACCESS not-accessible
			STATUS current
			DESCRIPTION
				"Information about a particular current sensor."
			INDEX { b3Target }
			::= { blade3SensorTargetTable 1 }
		
		Blade3SensorTargetEntry ::=
			SEQUENCE { 
				b3Target
					DisplayString,
				b3Current
					DisplayString,
				b3ThresholdsAll
					DisplayString,
				b3UpperCritical
					DisplayString,
				b3UpperNonCritical
					DisplayString,
				b3UpperNonRecoverable
					DisplayString,
				b3LowerNonCritical
					DisplayString,
				b3LowerCritical
					DisplayString,
				b3LowerNonRecoverable
					DisplayString,
				b3SensorHealth
					INTEGER,
				b3SensorHealthEvents
					DisplayString,
				b3NegativeHysteresis
					DisplayString,
				b3PositiveHysteresis
					DisplayString,
				b3SensorType
					DisplayString,
				b3SensorFRUInfo
					DisplayString
			 }

 		b3Target OBJECT-TYPE
			SYNTAX DisplayString
			MAX-ACCESS not-accessible
			STATUS current
			DESCRIPTION
				"sensor Name"
			::= { blade3SensorTargetEntry 1 }
		
 		b3Current OBJECT-TYPE
			SYNTAX DisplayString
			MAX-ACCESS read-only
			STATUS current
			DESCRIPTION
				"Display the current value of a sensor."
			::= { blade3SensorTargetEntry 2 }
		
 		b3ThresholdsAll OBJECT-TYPE
			SYNTAX DisplayString
			MAX-ACCESS read-only
			STATUS current
			DESCRIPTION
				"All thresholds of a sensor"
			::= { blade3SensorTargetEntry 3 }
		
 		b3UpperCritical OBJECT-TYPE
			SYNTAX DisplayString
			MAX-ACCESS read-write
			STATUS current
			DESCRIPTION
				"Upper critical thresholds"
			::= { blade3SensorTargetEntry 4 }
		
 		b3UpperNonCritical OBJECT-TYPE
			SYNTAX DisplayString
			MAX-ACCESS read-write
			STATUS current
			DESCRIPTION
				"Upper non-critical thresholds"
			::= { blade3SensorTargetEntry 5 }
		
 		b3UpperNonRecoverable OBJECT-TYPE
			SYNTAX DisplayString
			MAX-ACCESS read-write
			STATUS current
			DESCRIPTION
				"Upper non-recoverable thresholds"
			::= { blade3SensorTargetEntry 6 }
		
 		b3LowerNonCritical OBJECT-TYPE
			SYNTAX DisplayString
			MAX-ACCESS read-write
			STATUS current
			DESCRIPTION
				"Lower non-critical thresholds"
			::= { blade3SensorTargetEntry 7 }
		
 		b3LowerCritical OBJECT-TYPE
			SYNTAX DisplayString
			MAX-ACCESS read-write
			STATUS current
			DESCRIPTION
				"Lower critical thresholds"
			::= { blade3SensorTargetEntry 8 }
		
 		b3LowerNonRecoverable OBJECT-TYPE
			SYNTAX DisplayString
			MAX-ACCESS read-write
			STATUS current
			DESCRIPTION
				"Lower non-recoverable thresholds"
			::= { blade3SensorTargetEntry 9 }
		
 		b3SensorHealth OBJECT-TYPE
			SYNTAX INTEGER
				{
				ok(0),
				minor(1),
				major(2),
				critical(3)
				}
			MAX-ACCESS read-only
			STATUS current
			DESCRIPTION
				"b3Health information about a particular b2Location. 
				This will be one of the following:
				(0-ok, 1-minor, 2-major, 3-critical)"
			::= { blade3SensorTargetEntry 10 }
		
 		b3SensorHealthEvents OBJECT-TYPE
			SYNTAX DisplayString
			MAX-ACCESS read-only
			STATUS current
			DESCRIPTION
				"Events that contribute to the b3Health of the b2Location.  
				This is a list of events currently happening on the 
				b3Location."
			::= { blade3SensorTargetEntry 11 }
		
		
 		b3NegativeHysteresis OBJECT-TYPE
			SYNTAX DisplayString
			MAX-ACCESS read-write
			STATUS current
			DESCRIPTION
				"Get/Set the negativeHysteresis value."
			::= { blade3SensorTargetEntry 16 }
		
 		b3PositiveHysteresis OBJECT-TYPE
			SYNTAX DisplayString
			MAX-ACCESS read-write
			STATUS current
			DESCRIPTION
				"Get/Set the positiveHysteresis value."
			::= { blade3SensorTargetEntry 17 }
		
 		b3SensorType OBJECT-TYPE
			SYNTAX DisplayString
			MAX-ACCESS read-only
			STATUS current
			DESCRIPTION
				"Get the type of the sensor."
			::= { blade3SensorTargetEntry 18 }
		
 		b3SensorFRUInfo OBJECT-TYPE
			SYNTAX DisplayString
			MAX-ACCESS read-only
			STATUS current
			DESCRIPTION
				"Get the fruinfo of the sensor."
			::= { blade3SensorTargetEntry 19 }
		
 		blade3FruTable OBJECT-TYPE
			SYNTAX SEQUENCE OF Blade3FruEntry
			MAX-ACCESS not-accessible
			STATUS current
			DESCRIPTION
				"A table containing the list of FRU information."
			::= { blade3 2002 }
		
 		blade3FruEntry OBJECT-TYPE
			SYNTAX Blade3FruEntry
			MAX-ACCESS not-accessible
			STATUS current
			DESCRIPTION
				"Information about a particular current FRU."
			INDEX { b3fruNumber }
			::= { blade3FruTable 1 }
		
		Blade3FruEntry ::=
			SEQUENCE { 
				b3fruNumber
					INTEGER,
				b3FruHotSwapState
					DisplayString,
				b3FruLedProperties
					DisplayString,
				b3FRUControl
					INTEGER,
				b3FRULabel
					DisplayString,
				b3ResetReason
					DisplayString
			 }

 		b3fruNumber OBJECT-TYPE
			SYNTAX INTEGER
			MAX-ACCESS not-accessible
			STATUS current
			DESCRIPTION
				" "
			::= { blade3FruEntry 1 }
		
 		b3FruHotSwapState OBJECT-TYPE
			SYNTAX DisplayString
			MAX-ACCESS read-only
			STATUS current
			DESCRIPTION
				"Retrieve the hot swap state of the FRU from the 
				internally known hot swap states of blade3."
			::= { blade3FruEntry 3 }
		
 		b3FruLedProperties OBJECT-TYPE
			SYNTAX DisplayString
			MAX-ACCESS read-only
			STATUS current
			DESCRIPTION
				"Retrieves the LED support information from a FRU. Returns a comma separated
				list of LEDS and the number of FRU supported user LEDs."
			::= { blade3FruEntry 4 }

		

		b3FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade3FruEntry 9 }
		
 		b3FRULabel OBJECT-TYPE
			SYNTAX DisplayString
			MAX-ACCESS read-only
			STATUS current
			DESCRIPTION
				"Get fru label of blade3."
			::= { blade3FruEntry 10 }
		
 		b3ResetReason OBJECT-TYPE
			SYNTAX DisplayString
			MAX-ACCESS read-only
			STATUS current
			DESCRIPTION
				"Delete fru label of smm."
			::= { blade3FruEntry 11 }
		
 		blade3FruLedTable OBJECT-TYPE
			SYNTAX SEQUENCE OF Blade3FruLedEntry
			MAX-ACCESS not-accessible
			STATUS current
			DESCRIPTION
				"A table containing the list of led information."
			::= { blade3 2003 }
		
 		blade3FruLedEntry OBJECT-TYPE
			SYNTAX Blade3FruLedEntry
			MAX-ACCESS not-accessible
			STATUS current
			DESCRIPTION
				"Information about a particular current led."
			INDEX { b3FruID, b3FruLed }
			::= { blade3FruLedTable 1 }
		
		Blade3FruLedEntry ::=
			SEQUENCE { 
				b3FruID
					INTEGER,
				b3FruLed
					DisplayString,
				b3FruLedColorProps
					DisplayString,
				b3FruLedState
					DisplayString
			 }

 		b3FruID OBJECT-TYPE
			SYNTAX INTEGER
			MAX-ACCESS not-accessible
			STATUS current
			DESCRIPTION
				" "
			::= { blade3FruLedEntry 1 }
		
 		b3FruLed OBJECT-TYPE
			SYNTAX DisplayString
			MAX-ACCESS not-accessible
			STATUS current
			DESCRIPTION
				" "
			::= { blade3FruLedEntry 2 }
		
 		b3FruLedColorProps OBJECT-TYPE
			SYNTAX DisplayString
			MAX-ACCESS read-only
			STATUS current
			DESCRIPTION
				"Finds out what colors are supported by the LED"
			::= { blade3FruLedEntry 3 }
		
 		b3FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade3FruLedEntry 4 }
		
 		blade3FruDescriptionTable OBJECT-TYPE
			SYNTAX SEQUENCE OF Blade3FruDescriptionEntry
			MAX-ACCESS not-accessible
			STATUS current
			DESCRIPTION
				"A table containing the list of blade3 FRU information."
			::= { blade3 2004 }
		
 		blade3FruDescriptionEntry OBJECT-TYPE
			SYNTAX Blade3FruDescriptionEntry
			MAX-ACCESS not-accessible
			STATUS current
			DESCRIPTION
				"Information about a particular current FRU."
			INDEX { b3fruNum }
			::= { blade3FruDescriptionTable 1 }
		
		Blade3FruDescriptionEntry ::=
			SEQUENCE { 
				b3fruNum
					INTEGER,
				b3fruBoardDescription
					DisplayString,
				b3fruBoardManufacturer
					DisplayString,
				b3fruBoardPartNumber
					DisplayString,
				b3fruBoardSerialNumber
					DisplayString,
				b3fruBoardManufactureDate
					DisplayString,
				b3fruProductDescription
					DisplayString,
				b3fruProductManufacturer
					DisplayString,
				b3fruProductPartNumber
					DisplayString,
				b3fruProductSerialNumber
					DisplayString,
				b3fruProductRevision
					DisplayString,
				b3fruAll
					DisplayString
			 }

 		b3fruNum OBJECT-TYPE
			SYNTAX INTEGER
			MAX-ACCESS not-accessible
			STATUS current
			DESCRIPTION
				"blade3 FRU's INDEX"
			::= { blade3FruDescriptionEntry 1 }
		
 		b3fruBoardDescription OBJECT-TYPE
			SYNTAX DisplayString
			MAX-ACCESS read-only
			STATUS current
			DESCRIPTION
				"Used to read the Board Description from the blade3 fru."
			::= { blade3FruDescriptionEntry 2 }
		
 		b3fruBoardManufacturer OBJECT-TYPE
			SYNTAX DisplayString
			MAX-ACCESS read-only
			STATUS current
			DESCRIPTION
				"Used to read the Board Manufacturer from the blade3 fru."
			::= { blade3FruDescriptionEntry 3 }
		
 		b3fruBoardPartNumber OBJECT-TYPE
			SYNTAX DisplayString
			MAX-ACCESS read-only
			STATUS current
			DESCRIPTION
				"Used to read the Board Part Number from the blade3 fru."
			::= { blade3FruDescriptionEntry 4 }
		
 		b3fruBoardSerialNumber OBJECT-TYPE
			SYNTAX DisplayString
			MAX-ACCESS read-only
			STATUS current
			DESCRIPTION
				"Used to read the Board Serial Number from the blade3 fru."
			::= { blade3FruDescriptionEntry 5 }
		
 		b3fruBoardManufactureDate OBJECT-TYPE
			SYNTAX DisplayString
			MAX-ACCESS read-only
			STATUS current
			DESCRIPTION
				"Used to read the Board Manufacture Date from the blade3 fru."
			::= { blade3FruDescriptionEntry 6 }
		
 		b3fruProductDescription OBJECT-TYPE
			SYNTAX DisplayString
			MAX-ACCESS read-only
			STATUS current
			DESCRIPTION
				"Used to read the Product Description from the blade3 fru."
			::= { blade3FruDescriptionEntry 7 }
		
 		b3fruProductManufacturer OBJECT-TYPE
			SYNTAX DisplayString
			MAX-ACCESS read-only
			STATUS current
			DESCRIPTION
				"Used to read the Product Manufacturer from the blade3 fru."
			::= { blade3FruDescriptionEntry 8 }
		
 		b3fruProductPartNumber OBJECT-TYPE
			SYNTAX DisplayString
			MAX-ACCESS read-only
			STATUS current
			DESCRIPTION
				"Used to read the Product Part Number from the blade3 fru."
			::= { blade3FruDescriptionEntry 9 }
		
 		b3fruProductSerialNumber OBJECT-TYPE
			SYNTAX DisplayString
			MAX-ACCESS read-only
			STATUS current
			DESCRIPTION
				"Used to read the Product Serial Number from the blade3 fru."
			::= { blade3FruDescriptionEntry 10 }
		
 		b3fruProductRevision OBJECT-TYPE
			SYNTAX DisplayString
			MAX-ACCESS read-only
			STATUS current
			DESCRIPTION
				"Used to read the Product Revision from the blade3 fru."
			::= { blade3FruDescriptionEntry 13 }
		
 		b3fruAll OBJECT-TYPE
			SYNTAX DisplayString
			MAX-ACCESS read-only
			STATUS current
			DESCRIPTION
				"Used to read the fru info all."
			::= { blade3FruDescriptionEntry 14 }
		
		blade3CPUTable OBJECT-TYPE
			SYNTAX SEQUENCE OF Blade3CPUEntry
			MAX-ACCESS not-accessible
			STATUS current
			DESCRIPTION
				"A table containing the list of Blade1 FRU information."
			::= { blade3 2006 }
		
		blade3CPUEntry OBJECT-TYPE
			SYNTAX Blade3CPUEntry
			MAX-ACCESS not-accessible
			STATUS current
			DESCRIPTION
				"Information about a particular current FRU."
			INDEX { b3CPUIndex }
			::= { blade3CPUTable 1 }
		
		Blade3CPUEntry ::=
			SEQUENCE { 
				b3CPUIndex
					INTEGER,
				b3CPUMark
					DisplayString,
				b3CPUInfo
					DisplayString,
				b3CPUPresent
					INTEGER,
				b3CPUHealth
					INTEGER,
				b3CPULocation
					DisplayString
			 }

		b3CPUIndex OBJECT-TYPE
			SYNTAX INTEGER
			MAX-ACCESS not-accessible
			STATUS current
			DESCRIPTION
				"CPU INDEX"
			::= { blade3CPUEntry 1 }
		
		b3CPUMark OBJECT-TYPE
			SYNTAX DisplayString
			MAX-ACCESS read-only
			STATUS current
			DESCRIPTION
				"Get the CPU silk-screen."
			::= { blade3CPUEntry 2 }
		
		b3CPUInfo OBJECT-TYPE
			SYNTAX DisplayString
			MAX-ACCESS read-only
			STATUS current
			DESCRIPTION
				"Get the CPU description of vendor, type and frequency."
			::= { blade3CPUEntry 3 }
		
		b3CPUPresent OBJECT-TYPE
			SYNTAX INTEGER
			MAX-ACCESS read-only
			STATUS current
			DESCRIPTION
				"Get the CPU presence status."
			::= { blade3CPUEntry 4 }
		
		b3CPUHealth OBJECT-TYPE
			SYNTAX INTEGER
			MAX-ACCESS read-only
			STATUS current
			DESCRIPTION
				"Get the CPU health status."
			::= { blade3CPUEntry 5 }
		
		b3CPULocation OBJECT-TYPE
			SYNTAX DisplayString
			MAX-ACCESS read-only
			STATUS current
			DESCRIPTION
				"Get the CPU location."
			::= { blade3CPUEntry 6 }
		
		blade3MemoryTable OBJECT-TYPE
			SYNTAX SEQUENCE OF Blade3MemoryEntry
			MAX-ACCESS not-accessible
			STATUS current
			DESCRIPTION
				"A table containing the list of Blade1 FRU information."
			::= { blade3 2007 }
		
		blade3MemoryEntry OBJECT-TYPE
			SYNTAX Blade3MemoryEntry
			MAX-ACCESS not-accessible
			STATUS current
			DESCRIPTION
				"Information about a particular current FRU."
			INDEX { b3MEMIndex }
			::= { blade3MemoryTable 1 }
		
		Blade3MemoryEntry ::=
			SEQUENCE { 
				b3MEMIndex
					INTEGER,
				b3MEMMark
					DisplayString,
				b3MEMInfo
					DisplayString,
				b3MEMPresent
					INTEGER,
				b3MEMHealth
					INTEGER,
				b3MEMLocation
					DisplayString
			 }

		b3MEMIndex OBJECT-TYPE
			SYNTAX INTEGER
			MAX-ACCESS not-accessible
			STATUS current
			DESCRIPTION
				"MEMORY INDEX"
			::= { blade3MemoryEntry 1 }
		
		b3MEMMark OBJECT-TYPE
			SYNTAX DisplayString
			MAX-ACCESS read-only
			STATUS current
			DESCRIPTION
				"Get the memory silk-screen."
			::= { blade3MemoryEntry 2 }
		
		b3MEMInfo OBJECT-TYPE
			SYNTAX DisplayString
			MAX-ACCESS read-only
			STATUS current
			DESCRIPTION
				"Get the memory description of vendor, frequency and capacity."
			::= { blade3MemoryEntry 3 }
		
		b3MEMPresent OBJECT-TYPE
			SYNTAX INTEGER
			MAX-ACCESS read-only
			STATUS current
			DESCRIPTION
				"Get the memory presence status."
			::= { blade3MemoryEntry 4 }
		
		b3MEMHealth OBJECT-TYPE
			SYNTAX INTEGER
			MAX-ACCESS read-only
			STATUS current
			DESCRIPTION
				"Get the memory health status."
			::= { blade3MemoryEntry 5 }
		
		b3MEMLocation OBJECT-TYPE
			SYNTAX DisplayString
			MAX-ACCESS read-only
			STATUS current
			DESCRIPTION
				"Get the memory location."
			::= { blade3MemoryEntry 6 }
		
		blade3MezzTable OBJECT-TYPE
			SYNTAX SEQUENCE OF Blade3MezzEntry
			MAX-ACCESS not-accessible
			STATUS current
			DESCRIPTION
				"A table containing the list of Blade1 FRU information."
			::= { blade3 2008 }
		
		blade3MezzEntry OBJECT-TYPE
			SYNTAX Blade3MezzEntry
			MAX-ACCESS not-accessible
			STATUS current
			DESCRIPTION
				"Information about a particular current FRU."
			INDEX { b3MezzIndex }
			::= { blade3MezzTable 1 }
		
		Blade3MezzEntry ::=
			SEQUENCE { 
				b3MezzIndex
					INTEGER,
				b3MezzMark
					DisplayString,
				b3MezzInfo
					DisplayString,
				b3MezzPresent
					INTEGER,
				b3MezzHealth
					INTEGER,
				b3MezzLocation
					DisplayString,
				b3MezzMac
					DisplayString
			 }

		b3MezzIndex OBJECT-TYPE
			SYNTAX INTEGER
			MAX-ACCESS not-accessible
			STATUS current
			DESCRIPTION
				"MEZZ INDEX"
			::= { blade3MezzEntry 1 }
		
		b3MezzMark OBJECT-TYPE
			SYNTAX DisplayString
			MAX-ACCESS read-only
			STATUS current
			DESCRIPTION
				"Get the MEZZ silk-screen."
			::= { blade3MezzEntry 2 }
		
		b3MezzInfo OBJECT-TYPE
			SYNTAX DisplayString
			MAX-ACCESS read-only
			STATUS current
			DESCRIPTION
				"Get the MEZZ description of type."
			::= { blade3MezzEntry 3 }
		
		b3MezzPresent OBJECT-TYPE
			SYNTAX INTEGER
			MAX-ACCESS read-only
			STATUS current
			DESCRIPTION
				"Get the MEZZ presence status."
			::= { blade3MezzEntry 4 }
		
		b3MezzHealth OBJECT-TYPE
			SYNTAX INTEGER
			MAX-ACCESS read-only
			STATUS current
			DESCRIPTION
				"Get the MEZZ health status."
			::= { blade3MezzEntry 5 }
		
		b3MezzLocation OBJECT-TYPE
			SYNTAX DisplayString
			MAX-ACCESS read-only
			STATUS current
			DESCRIPTION
				"Get the MEZZ location."
			::= { blade3MezzEntry 6 }
		
		b3MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade3MezzEntry 7 }
		
		blade3DiskTable OBJECT-TYPE
			SYNTAX SEQUENCE OF Blade3DiskEntry
			MAX-ACCESS not-accessible
			STATUS current
			DESCRIPTION
				"A table containing the list of Blade1 FRU information."
			::= { blade3 2009 }
		
		blade3DiskEntry OBJECT-TYPE
			SYNTAX Blade3DiskEntry
			MAX-ACCESS not-accessible
			STATUS current
			DESCRIPTION
				"Information about a particular current FRU."
			INDEX { b3DiskIndex }
			::= { blade3DiskTable 1 }
		
		Blade3DiskEntry ::=
			SEQUENCE { 
				b3DiskIndex
					INTEGER,
				b3DiskMark
					DisplayString,
				b3DiskInfo
					DisplayString,
				b3DiskPresent
					INTEGER,
				b3DiskHealth
					INTEGER,
				b3DiskLocation
					DisplayString
			 }

		b3DiskIndex OBJECT-TYPE
			SYNTAX INTEGER
			MAX-ACCESS not-accessible
			STATUS current
			DESCRIPTION
				"DISK INDEX"
			::= { blade3DiskEntry 1 }
		
		b3DiskMark OBJECT-TYPE
			SYNTAX DisplayString
			MAX-ACCESS read-only
			STATUS current
			DESCRIPTION
				"Get the disk silk-screen."
			::= { blade3DiskEntry 2 }
		
		b3DiskInfo OBJECT-TYPE
			SYNTAX DisplayString
			MAX-ACCESS read-only
			STATUS current
			DESCRIPTION
				"Get the disk description of vendor, capacity and speed."
			::= { blade3DiskEntry 3 }
		
		b3DiskPresent OBJECT-TYPE
			SYNTAX INTEGER
			MAX-ACCESS read-only
			STATUS current
			DESCRIPTION
				"Get the disk presence status."
			::= { blade3DiskEntry 4 }
		
		b3DiskHealth OBJECT-TYPE
			SYNTAX INTEGER
			MAX-ACCESS read-only
			STATUS current
			DESCRIPTION
				"Get the disk health status."
			::= { blade3DiskEntry 5 }
		
		b3DiskLocation OBJECT-TYPE
			SYNTAX DisplayString
			MAX-ACCESS read-only
			STATUS current
			DESCRIPTION
				"Get the disk location."
			::= { blade3DiskEntry 6 }
		
		blade3SecretKvmVmmTable OBJECT-TYPE
			SYNTAX SEQUENCE OF Blade3SecretKvmVmmEntry
			MAX-ACCESS not-accessible
			STATUS current
			DESCRIPTION
				"A table containing the list of Blade3 KVM&VMM secret information."
			::= { blade3 2010 }

		blade3SecretKvmVmmEntry OBJECT-TYPE
			SYNTAX Blade3SecretKvmVmmEntry
			MAX-ACCESS not-accessible
			STATUS current
			DESCRIPTION
				"Information about a particular current KVM&VMM."
			INDEX { b3SecretKvmVmmIndex }
			::= { blade3SecretKvmVmmTable 1 }
		Blade3SecretKvmVmmEntry ::=
			SEQUENCE { 
				b3SecretKvmVmmIndex
					INTEGER,
				b3SecretKvmState
					INTEGER,
				b3SecretVmmState
					INTEGER,
				b3MMSecretVmmKey
					DisplayString,
				b3SecretVmmKey
					DisplayString
			 }
		b3SecretKvmVmmIndex OBJECT-TYPE
			SYNTAX INTEGER
			MAX-ACCESS not-accessible
			STATUS current
			DESCRIPTION
				"KVM&VMM INDEX."
			::= { blade3SecretKvmVmmEntry 1 }
		b3SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade3SecretKvmVmmEntry 2 }
		b3SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade3SecretKvmVmmEntry 3 }
		b3MMSecretVmmKey OBJECT-TYPE
			SYNTAX DisplayString
			MAX-ACCESS read-only
			STATUS current
			DESCRIPTION
				"Get the MM secret VMM key."
			::= { blade3SecretKvmVmmEntry 4 }
		b3SecretVmmKey OBJECT-TYPE
			SYNTAX DisplayString
			MAX-ACCESS read-write
			STATUS current
			DESCRIPTION
				"Set the secret VMM key."
			::= { blade3SecretKvmVmmEntry 5 }
		blade4 OBJECT IDENTIFIER ::= { blades 4 }

		
 		b4DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade4 4 }
		
 		b4PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade4 5 }
		
 		b4Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade4 6 }

		
 		b4Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b4Health information about a particular b4Location. 
				This will be one of the following:
				(0-ok, 1-minor, 2-major, 3-majorandminor,4-critical,5-criticalandminor,6-criticalandmajor,7-criticalandmajorandminor)"
			::= { blade4 8 }
		
 		b4HealthEvents OBJECT-TYPE
			SYNTAX DisplayString
			MAX-ACCESS read-only
			STATUS current
			DESCRIPTION
				"Events that contribute to the b4Health of the b4Location.  
				This is a list of events currently happening on the 
				b4Location."
			::= { blade4 9 }
		
 		b4ClearSEL OBJECT-TYPE
			SYNTAX INTEGER { clear(1) }
			MAX-ACCESS read-write
			STATUS current
			DESCRIPTION
				"Clean the BMC's SEL on the board."
			::= { blade4 12 }
		
 		b4ExDiskBoardPresence OBJECT-TYPE
			SYNTAX INTEGER
				{
				not-present(0),
				present(1)
				}
			MAX-ACCESS read-only
			STATUS current
			DESCRIPTION
				"Used to find out if the extended disk board is present.
				0 - not present
				1 - present"
			::= { blade4 14 }
		
 		b4BladeVersion OBJECT-TYPE
			SYNTAX DisplayString
			MAX-ACCESS read-only
			STATUS current
			DESCRIPTION
				"display the Version of board4."
			::= { blade4 20 }
		
 		b4MACAddress OBJECT-TYPE
			SYNTAX DisplayString
			MAX-ACCESS read-only
			STATUS current
			DESCRIPTION
				"display the MACAddress of board4."
			::= { blade4 21 }
		
				
							
		
 		b4Safepwofftime OBJECT-TYPE
			SYNTAX INTEGER
			MAX-ACCESS read-write
			STATUS current
			DESCRIPTION
				"the safe poweroff time.
				"
			::= { blade4 26 }
		
 		b4BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade4 32 }
		
 		b4Systeminfo OBJECT-TYPE
			SYNTAX DisplayString
			MAX-ACCESS read-write
			STATUS current
			DESCRIPTION
				"display the system information of board4."
			::= { blade4 36 }

		
 		b4SystemProperties OBJECT-TYPE
			SYNTAX DisplayString
			MAX-ACCESS read-only
			STATUS current
			DESCRIPTION
				"Get the power of blade1."
			::= { blade4 39 }
		
 		b4BiosCfg OBJECT-TYPE
			SYNTAX DisplayString
			MAX-ACCESS read-write
			STATUS current
			DESCRIPTION
				"Get the power of blade1."
			::= { blade4 40 }
		
 		b4WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade4 41 }
		
 		b4RealTimePower OBJECT-TYPE
			SYNTAX INTEGER
			MAX-ACCESS read-only
			STATUS current
			DESCRIPTION
				" "
			::= { blade4 43 }
		
 		b4PowerCapping OBJECT-TYPE
			SYNTAX DisplayString
			MAX-ACCESS read-write
			STATUS current
			DESCRIPTION
				" "
			::= { blade4 44 }
		
 		b4Powerreference OBJECT-TYPE
			SYNTAX INTEGER
			MAX-ACCESS read-only
			STATUS current
			DESCRIPTION
				" "
			::= { blade4 45 }
		
 		b4ClearBiosConfig OBJECT-TYPE
			SYNTAX INTEGER
			MAX-ACCESS read-write
			STATUS current
			DESCRIPTION
				" "
			::= { blade4 46 }
		
 		b4BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade4 47 }
		
 		b4BmcUserAdd OBJECT-TYPE
			SYNTAX DisplayString
			MAX-ACCESS read-write
			STATUS current
			DESCRIPTION
				"Used to Add the BMC User
				settable format:
				username,passwd"
			::= { blade4 48 }
		
 		b4BmcUserDel OBJECT-TYPE
			SYNTAX DisplayString
			MAX-ACCESS read-write
			STATUS current
			DESCRIPTION
				"Used to Del the BMC User
				settable format:
				username"
			::= { blade4 49 }
		
 		b4BmcUserPasswd OBJECT-TYPE
			SYNTAX DisplayString
			MAX-ACCESS read-write
			STATUS current
			DESCRIPTION
				"Used to Change the BMC User Passwd
				settable format:
				username,passwd"
			::= { blade4 50 }
		
 		b4BmcUserpropertychg OBJECT-TYPE
			SYNTAX DisplayString
			MAX-ACCESS read-write
			STATUS current
			DESCRIPTION
				"Used to Change the BMC User Property
				settable format:
				username,property"
			::= { blade4 51 }
		
 		b4BmcGateway OBJECT-TYPE
			SYNTAX DisplayString
			MAX-ACCESS read-write
			STATUS current
			DESCRIPTION
				"Read or set the gateway."
			::= { blade4 52 }
		
 		b4SlotBitmap OBJECT-TYPE
			SYNTAX INTEGER
			MAX-ACCESS read-only
			STATUS current
			DESCRIPTION
				" "
			::= { blade4 55 }
		
		b4systemGuid OBJECT-TYPE
			SYNTAX DisplayString
			MAX-ACCESS read-only
			STATUS current
			DESCRIPTION
				" "
			::= { blade4 56 }
		
		b4ProductName OBJECT-TYPE
			SYNTAX DisplayString
			MAX-ACCESS read-only
			STATUS current
			DESCRIPTION
				"display the Version of board4."
			::= { blade4 57 }

		b4BundleVersion OBJECT-TYPE
			SYNTAX DisplayString
			MAX-ACCESS read-write
			STATUS current
			DESCRIPTION
				"Get or set the board4 bundle version."
			::= { blade4 58 }

 		blade4SensorTargetTable OBJECT-TYPE
			SYNTAX SEQUENCE OF Blade4SensorTargetEntry
			MAX-ACCESS not-accessible
			STATUS current
			DESCRIPTION
				"A table containing the list of sensor information."
			::= { blade4 2001 }
		
 		blade4SensorTargetEntry OBJECT-TYPE
			SYNTAX Blade4SensorTargetEntry
			MAX-ACCESS not-accessible
			STATUS current
			DESCRIPTION
				"Information about a particular current sensor."
			INDEX { b4Target }
			::= { blade4SensorTargetTable 1 }
		
		Blade4SensorTargetEntry ::=
			SEQUENCE { 
				b4Target
					DisplayString,
				b4Current
					DisplayString,
				b4ThresholdsAll
					DisplayString,
				b4UpperCritical
					DisplayString,
				b4UpperNonCritical
					DisplayString,
				b4UpperNonRecoverable
					DisplayString,
				b4LowerNonCritical
					DisplayString,
				b4LowerCritical
					DisplayString,
				b4LowerNonRecoverable
					DisplayString,
				b4SensorHealth
					INTEGER,
				b4SensorHealthEvents
					DisplayString,
				b4NegativeHysteresis
					DisplayString,
				b4PositiveHysteresis
					DisplayString,
				b4SensorType
					DisplayString,
				b4SensorFRUInfo
					DisplayString
			 }

 		b4Target OBJECT-TYPE
			SYNTAX DisplayString
			MAX-ACCESS not-accessible
			STATUS current
			DESCRIPTION
				"sensor Name"
			::= { blade4SensorTargetEntry 1 }
		
 		b4Current OBJECT-TYPE
			SYNTAX DisplayString
			MAX-ACCESS read-only
			STATUS current
			DESCRIPTION
				"Display the current value of a sensor."
			::= { blade4SensorTargetEntry 2 }
		
 		b4ThresholdsAll OBJECT-TYPE
			SYNTAX DisplayString
			MAX-ACCESS read-only
			STATUS current
			DESCRIPTION
				"All thresholds of a sensor"
			::= { blade4SensorTargetEntry 3 }
		
 		b4UpperCritical OBJECT-TYPE
			SYNTAX DisplayString
			MAX-ACCESS read-write
			STATUS current
			DESCRIPTION
				"Upper critical thresholds"
			::= { blade4SensorTargetEntry 4 }
		
 		b4UpperNonCritical OBJECT-TYPE
			SYNTAX DisplayString
			MAX-ACCESS read-write
			STATUS current
			DESCRIPTION
				"Upper non-critical thresholds"
			::= { blade4SensorTargetEntry 5 }
		
 		b4UpperNonRecoverable OBJECT-TYPE
			SYNTAX DisplayString
			MAX-ACCESS read-write
			STATUS current
			DESCRIPTION
				"Upper non-recoverable thresholds"
			::= { blade4SensorTargetEntry 6 }
		
 		b4LowerNonCritical OBJECT-TYPE
			SYNTAX DisplayString
			MAX-ACCESS read-write
			STATUS current
			DESCRIPTION
				"Lower non-critical thresholds"
			::= { blade4SensorTargetEntry 7 }
		
 		b4LowerCritical OBJECT-TYPE
			SYNTAX DisplayString
			MAX-ACCESS read-write
			STATUS current
			DESCRIPTION
				"Lower critical thresholds"
			::= { blade4SensorTargetEntry 8 }
		
 		b4LowerNonRecoverable OBJECT-TYPE
			SYNTAX DisplayString
			MAX-ACCESS read-write
			STATUS current
			DESCRIPTION
				"Lower non-recoverable thresholds"
			::= { blade4SensorTargetEntry 9 }
		
 		b4SensorHealth OBJECT-TYPE
			SYNTAX INTEGER
				{
				ok(0),
				minor(1),
				major(2),
				critical(3)
				}
			MAX-ACCESS read-only
			STATUS current
			DESCRIPTION
				"b4Health information about a particular b4Location. 
				This will be one of the following:
				(0-ok, 1-minor, 2-major, 3-critical)"
			::= { blade4SensorTargetEntry 10 }
		
 		b4SensorHealthEvents OBJECT-TYPE
			SYNTAX DisplayString
			MAX-ACCESS read-only
			STATUS current
			DESCRIPTION
				"Events that contribute to the b4Health of the b4Location.  
				This is a list of events currently happening on the 
				b4Location."
			::= { blade4SensorTargetEntry 11 }
		
		
 		b4NegativeHysteresis OBJECT-TYPE
			SYNTAX DisplayString
			MAX-ACCESS read-write
			STATUS current
			DESCRIPTION
				"Get/Set the negativeHysteresis value."
			::= { blade4SensorTargetEntry 16 }
		
 		b4PositiveHysteresis OBJECT-TYPE
			SYNTAX DisplayString
			MAX-ACCESS read-write
			STATUS current
			DESCRIPTION
				"Get/Set the positiveHysteresis value."
			::= { blade4SensorTargetEntry 17 }
		
 		b4SensorType OBJECT-TYPE
			SYNTAX DisplayString
			MAX-ACCESS read-only
			STATUS current
			DESCRIPTION
				"Get the type of the sensor."
			::= { blade4SensorTargetEntry 18 }
		
 		b4SensorFRUInfo OBJECT-TYPE
			SYNTAX DisplayString
			MAX-ACCESS read-only
			STATUS current
			DESCRIPTION
				"Get the fruinfo of the sensor."
			::= { blade4SensorTargetEntry 19 }
		
 		blade4FruTable OBJECT-TYPE
			SYNTAX SEQUENCE OF Blade4FruEntry
			MAX-ACCESS not-accessible
			STATUS current
			DESCRIPTION
				"A table containing the list of FRU information."
			::= { blade4 2002 }
		
 		blade4FruEntry OBJECT-TYPE
			SYNTAX Blade4FruEntry
			MAX-ACCESS not-accessible
			STATUS current
			DESCRIPTION
				"Information about a particular current FRU."
			INDEX { b4fruNumber }
			::= { blade4FruTable 1 }
		
		Blade4FruEntry ::=
			SEQUENCE { 
				b4fruNumber
					INTEGER,
				b4FruHotSwapState
					DisplayString,
				b4FruLedProperties
					DisplayString,
				b4FRUControl
					INTEGER,
				b4FRULabel
					DisplayString,
				b4ResetReason
					DisplayString
			 }

 		b4fruNumber OBJECT-TYPE
			SYNTAX INTEGER
			MAX-ACCESS not-accessible
			STATUS current
			DESCRIPTION
				" "
			::= { blade4FruEntry 1 }
		
 		b4FruHotSwapState OBJECT-TYPE
			SYNTAX DisplayString
			MAX-ACCESS read-only
			STATUS current
			DESCRIPTION
				"Retrieve the hot swap state of the FRU from the 
				internally known hot swap states of blade4."
			::= { blade4FruEntry 3 }
		
 		b4FruLedProperties OBJECT-TYPE
			SYNTAX DisplayString
			MAX-ACCESS read-only
			STATUS current
			DESCRIPTION
				"Retrieves the LED support information from a FRU. Returns a comma separated
				list of LEDS and the number of FRU supported user LEDs."
			::= { blade4FruEntry 4 }

		

		b4FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade4FruEntry 9 }
		
 		b4FRULabel OBJECT-TYPE
			SYNTAX DisplayString
			MAX-ACCESS read-only
			STATUS current
			DESCRIPTION
				"Get fru label of blade4."
			::= { blade4FruEntry 10 }
		
 		b4ResetReason OBJECT-TYPE
			SYNTAX DisplayString
			MAX-ACCESS read-only
			STATUS current
			DESCRIPTION
				"Delete fru label of smm."
			::= { blade4FruEntry 11 }
		
 		blade4FruLedTable OBJECT-TYPE
			SYNTAX SEQUENCE OF Blade4FruLedEntry
			MAX-ACCESS not-accessible
			STATUS current
			DESCRIPTION
				"A table containing the list of led information."
			::= { blade4 2003 }
		
 		blade4FruLedEntry OBJECT-TYPE
			SYNTAX Blade4FruLedEntry
			MAX-ACCESS not-accessible
			STATUS current
			DESCRIPTION
				"Information about a particular current led."
			INDEX { b4FruID, b4FruLed }
			::= { blade4FruLedTable 1 }
		
		Blade4FruLedEntry ::=
			SEQUENCE { 
				b4FruID
					INTEGER,
				b4FruLed
					DisplayString,
				b4FruLedColorProps
					DisplayString,
				b4FruLedState
					DisplayString
			 }

 		b4FruID OBJECT-TYPE
			SYNTAX INTEGER
			MAX-ACCESS not-accessible
			STATUS current
			DESCRIPTION
				" "
			::= { blade4FruLedEntry 1 }
		
 		b4FruLed OBJECT-TYPE
			SYNTAX DisplayString
			MAX-ACCESS not-accessible
			STATUS current
			DESCRIPTION
				" "
			::= { blade4FruLedEntry 2 }
		
 		b4FruLedColorProps OBJECT-TYPE
			SYNTAX DisplayString
			MAX-ACCESS read-only
			STATUS current
			DESCRIPTION
				"Finds out what colors are supported by the LED"
			::= { blade4FruLedEntry 3 }
		
 		b4FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade4FruLedEntry 4 }
		
 		blade4FruDescriptionTable OBJECT-TYPE
			SYNTAX SEQUENCE OF Blade4FruDescriptionEntry
			MAX-ACCESS not-accessible
			STATUS current
			DESCRIPTION
				"A table containing the list of blade4 FRU information."
			::= { blade4 2004 }
		
 		blade4FruDescriptionEntry OBJECT-TYPE
			SYNTAX Blade4FruDescriptionEntry
			MAX-ACCESS not-accessible
			STATUS current
			DESCRIPTION
				"Information about a particular current FRU."
			INDEX { b4fruNum }
			::= { blade4FruDescriptionTable 1 }
		
		Blade4FruDescriptionEntry ::=
			SEQUENCE { 
				b4fruNum
					INTEGER,
				b4fruBoardDescription
					DisplayString,
				b4fruBoardManufacturer
					DisplayString,
				b4fruBoardPartNumber
					DisplayString,
				b4fruBoardSerialNumber
					DisplayString,
				b4fruBoardManufactureDate
					DisplayString,
				b4fruProductDescription
					DisplayString,
				b4fruProductManufacturer
					DisplayString,
				b4fruProductPartNumber
					DisplayString,
				b4fruProductSerialNumber
					DisplayString,
				b4fruProductRevision
					DisplayString,
				b4fruAll
					DisplayString
			 }

 		b4fruNum OBJECT-TYPE
			SYNTAX INTEGER
			MAX-ACCESS not-accessible
			STATUS current
			DESCRIPTION
				"blade4 FRU's INDEX"
			::= { blade4FruDescriptionEntry 1 }
		
 		b4fruBoardDescription OBJECT-TYPE
			SYNTAX DisplayString
			MAX-ACCESS read-only
			STATUS current
			DESCRIPTION
				"Used to read the Board Description from the blade4 fru."
			::= { blade4FruDescriptionEntry 2 }
		
 		b4fruBoardManufacturer OBJECT-TYPE
			SYNTAX DisplayString
			MAX-ACCESS read-only
			STATUS current
			DESCRIPTION
				"Used to read the Board Manufacturer from the bladef4 fru."
			::= { blade4FruDescriptionEntry 3 }
		
 		b4fruBoardPartNumber OBJECT-TYPE
			SYNTAX DisplayString
			MAX-ACCESS read-only
			STATUS current
			DESCRIPTION
				"Used to read the Board Part Number from the blade4 fru."
			::= { blade4FruDescriptionEntry 4 }
		
 		b4fruBoardSerialNumber OBJECT-TYPE
			SYNTAX DisplayString
			MAX-ACCESS read-only
			STATUS current
			DESCRIPTION
				"Used to read the Board Serial Number from the blade4 fru."
			::= { blade4FruDescriptionEntry 5 }
		
 		b4fruBoardManufactureDate OBJECT-TYPE
			SYNTAX DisplayString
			MAX-ACCESS read-only
			STATUS current
			DESCRIPTION
				"Used to read the Board Manufacture Date from the blade4 fru."
			::= { blade4FruDescriptionEntry 6 }
		
 		b4fruProductDescription OBJECT-TYPE
			SYNTAX DisplayString
			MAX-ACCESS read-only
			STATUS current
			DESCRIPTION
				"Used to read the Product Description from the blade4 fru."
			::= { blade4FruDescriptionEntry 7 }
		
 		b4fruProductManufacturer OBJECT-TYPE
			SYNTAX DisplayString
			MAX-ACCESS read-only
			STATUS current
			DESCRIPTION
				"Used to read the Product Manufacturer from the blade4 fru."
			::= { blade4FruDescriptionEntry 8 }
		
 		b4fruProductPartNumber OBJECT-TYPE
			SYNTAX DisplayString
			MAX-ACCESS read-only
			STATUS current
			DESCRIPTION
				"Used to read the Product Part Number from the blade4 fru."
			::= { blade4FruDescriptionEntry 9 }
		
 		b4fruProductSerialNumber OBJECT-TYPE
			SYNTAX DisplayString
			MAX-ACCESS read-only
			STATUS current
			DESCRIPTION
				"Used to read the Product Serial Number from the blade4 fru."
			::= { blade4FruDescriptionEntry 10 }
		
 		b4fruProductRevision OBJECT-TYPE
			SYNTAX DisplayString
			MAX-ACCESS read-only
			STATUS current
			DESCRIPTION
				"Used to read the Product Revision from the blade4 fru."
			::= { blade4FruDescriptionEntry 13 }
		
 		b4fruAll OBJECT-TYPE
			SYNTAX DisplayString
			MAX-ACCESS read-only
			STATUS current
			DESCRIPTION
				"Used to read the fru info all."
			::= { blade4FruDescriptionEntry 14 }
		
		blade4CPUTable OBJECT-TYPE
			SYNTAX SEQUENCE OF Blade4CPUEntry
			MAX-ACCESS not-accessible
			STATUS current
			DESCRIPTION
				"A table containing the list of Blade1 FRU information."
			::= { blade4 2006 }
		
		blade4CPUEntry OBJECT-TYPE
			SYNTAX Blade4CPUEntry
			MAX-ACCESS not-accessible
			STATUS current
			DESCRIPTION
				"Information about a particular current FRU."
			INDEX { b4CPUIndex }
			::= { blade4CPUTable 1 }
		
		Blade4CPUEntry ::=
			SEQUENCE { 
				b4CPUIndex
					INTEGER,
				b4CPUMark
					DisplayString,
				b4CPUInfo
					DisplayString,
				b4CPUPresent
					INTEGER,
				b4CPUHealth
					INTEGER,
				b4CPULocation
					DisplayString
			 }

		b4CPUIndex OBJECT-TYPE
			SYNTAX INTEGER
			MAX-ACCESS not-accessible
			STATUS current
			DESCRIPTION
				"CPU INDEX"
			::= { blade4CPUEntry 1 }
		
		b4CPUMark OBJECT-TYPE
			SYNTAX DisplayString
			MAX-ACCESS read-only
			STATUS current
			DESCRIPTION
				"Get the CPU silk-screen."
			::= { blade4CPUEntry 2 }
		
		b4CPUInfo OBJECT-TYPE
			SYNTAX DisplayString
			MAX-ACCESS read-only
			STATUS current
			DESCRIPTION
				"Get the CPU description of vendor, type and frequency."
			::= { blade4CPUEntry 3 }
		
		b4CPUPresent OBJECT-TYPE
			SYNTAX INTEGER
			MAX-ACCESS read-only
			STATUS current
			DESCRIPTION
				"Get the CPU presence status."
			::= { blade4CPUEntry 4 }
		
		b4CPUHealth OBJECT-TYPE
			SYNTAX INTEGER
			MAX-ACCESS read-only
			STATUS current
			DESCRIPTION
				"Get the CPU health status."
			::= { blade4CPUEntry 5 }
		
		b4CPULocation OBJECT-TYPE
			SYNTAX DisplayString
			MAX-ACCESS read-only
			STATUS current
			DESCRIPTION
				"Get the CPU location."
			::= { blade4CPUEntry 6 }
		
		blade4MemoryTable OBJECT-TYPE
			SYNTAX SEQUENCE OF Blade4MemoryEntry
			MAX-ACCESS not-accessible
			STATUS current
			DESCRIPTION
				"A table containing the list of Blade1 FRU information."
			::= { blade4 2007 }
		
		blade4MemoryEntry OBJECT-TYPE
			SYNTAX Blade4MemoryEntry
			MAX-ACCESS not-accessible
			STATUS current
			DESCRIPTION
				"Information about a particular current FRU."
			INDEX { b4MEMIndex }
			::= { blade4MemoryTable 1 }
		
		Blade4MemoryEntry ::=
			SEQUENCE { 
				b4MEMIndex
					INTEGER,
				b4MEMMark
					DisplayString,
				b4MEMInfo
					DisplayString,
				b4MEMPresent
					INTEGER,
				b4MEMHealth
					INTEGER,
				b4MEMLocation
					DisplayString
			 }

		b4MEMIndex OBJECT-TYPE
			SYNTAX INTEGER
			MAX-ACCESS not-accessible
			STATUS current
			DESCRIPTION
				"MEMORY INDEX"
			::= { blade4MemoryEntry 1 }
		
		b4MEMMark OBJECT-TYPE
			SYNTAX DisplayString
			MAX-ACCESS read-only
			STATUS current
			DESCRIPTION
				"Get the memory silk-screen."
			::= { blade4MemoryEntry 2 }
		
		b4MEMInfo OBJECT-TYPE
			SYNTAX DisplayString
			MAX-ACCESS read-only
			STATUS current
			DESCRIPTION
				"Get the memory description of vendor, frequency and capacity."
			::= { blade4MemoryEntry 3 }
		
		b4MEMPresent OBJECT-TYPE
			SYNTAX INTEGER
			MAX-ACCESS read-only
			STATUS current
			DESCRIPTION
				"Get the memory presence status."
			::= { blade4MemoryEntry 4 }
		
		b4MEMHealth OBJECT-TYPE
			SYNTAX INTEGER
			MAX-ACCESS read-only
			STATUS current
			DESCRIPTION
				"Get the memory health status."
			::= { blade4MemoryEntry 5 }
		
		b4MEMLocation OBJECT-TYPE
			SYNTAX DisplayString
			MAX-ACCESS read-only
			STATUS current
			DESCRIPTION
				"Get the memory location."
			::= { blade4MemoryEntry 6 }
		
		blade4MezzTable OBJECT-TYPE
			SYNTAX SEQUENCE OF Blade4MezzEntry
			MAX-ACCESS not-accessible
			STATUS current
			DESCRIPTION
				"A table containing the list of Blade1 FRU information."
			::= { blade4 2008 }
		
		blade4MezzEntry OBJECT-TYPE
			SYNTAX Blade4MezzEntry
			MAX-ACCESS not-accessible
			STATUS current
			DESCRIPTION
				"Information about a particular current FRU."
			INDEX { b4MezzIndex }
			::= { blade4MezzTable 1 }
		
		Blade4MezzEntry ::=
			SEQUENCE { 
				b4MezzIndex
					INTEGER,
				b4MezzMark
					DisplayString,
				b4MezzInfo
					DisplayString,
				b4MezzPresent
					INTEGER,
				b4MezzHealth
					INTEGER,
				b4MezzLocation
					DisplayString,
				b4MezzMac
					DisplayString
			 }

		b4MezzIndex OBJECT-TYPE
			SYNTAX INTEGER
			MAX-ACCESS not-accessible
			STATUS current
			DESCRIPTION
				"MEZZ INDEX"
			::= { blade4MezzEntry 1 }
		
		b4MezzMark OBJECT-TYPE
			SYNTAX DisplayString
			MAX-ACCESS read-only
			STATUS current
			DESCRIPTION
				"Get the MEZZ silk-screen."
			::= { blade4MezzEntry 2 }
		
		b4MezzInfo OBJECT-TYPE
			SYNTAX DisplayString
			MAX-ACCESS read-only
			STATUS current
			DESCRIPTION
				"Get the MEZZ description of type."
			::= { blade4MezzEntry 3 }
		
		b4MezzPresent OBJECT-TYPE
			SYNTAX INTEGER
			MAX-ACCESS read-only
			STATUS current
			DESCRIPTION
				"Get the MEZZ presence status."
			::= { blade4MezzEntry 4 }
		
		b4MezzHealth OBJECT-TYPE
			SYNTAX INTEGER
			MAX-ACCESS read-only
			STATUS current
			DESCRIPTION
				"Get the MEZZ health status."
			::= { blade4MezzEntry 5 }
		
		b4MezzLocation OBJECT-TYPE
			SYNTAX DisplayString
			MAX-ACCESS read-only
			STATUS current
			DESCRIPTION
				"Get the MEZZ location."
			::= { blade4MezzEntry 6 }
		
		b4MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade4MezzEntry 7 }
		
		blade4DiskTable OBJECT-TYPE
			SYNTAX SEQUENCE OF Blade4DiskEntry
			MAX-ACCESS not-accessible
			STATUS current
			DESCRIPTION
				"A table containing the list of Blade1 FRU information."
			::= { blade4 2009 }
		
		blade4DiskEntry OBJECT-TYPE
			SYNTAX Blade4DiskEntry
			MAX-ACCESS not-accessible
			STATUS current
			DESCRIPTION
				"Information about a particular current FRU."
			INDEX { b4DiskIndex }
			::= { blade4DiskTable 1 }
		
		Blade4DiskEntry ::=
			SEQUENCE { 
				b4DiskIndex
					INTEGER,
				b4DiskMark
					DisplayString,
				b4DiskInfo
					DisplayString,
				b4DiskPresent
					INTEGER,
				b4DiskHealth
					INTEGER,
				b4DiskLocation
					DisplayString
			 }

		b4DiskIndex OBJECT-TYPE
			SYNTAX INTEGER
			MAX-ACCESS not-accessible
			STATUS current
			DESCRIPTION
				"DISK INDEX"
			::= { blade4DiskEntry 1 }
		
		b4DiskMark OBJECT-TYPE
			SYNTAX DisplayString
			MAX-ACCESS read-only
			STATUS current
			DESCRIPTION
				"Get the disk silk-screen."
			::= { blade4DiskEntry 2 }
		
		b4DiskInfo OBJECT-TYPE
			SYNTAX DisplayString
			MAX-ACCESS read-only
			STATUS current
			DESCRIPTION
				"Get the disk description of vendor, capacity and speed."
			::= { blade4DiskEntry 3 }
		
		b4DiskPresent OBJECT-TYPE
			SYNTAX INTEGER
			MAX-ACCESS read-only
			STATUS current
			DESCRIPTION
				"Get the disk presence status."
			::= { blade4DiskEntry 4 }
		
		b4DiskHealth OBJECT-TYPE
			SYNTAX INTEGER
			MAX-ACCESS read-only
			STATUS current
			DESCRIPTION
				"Get the disk health status."
			::= { blade4DiskEntry 5 }
		
		b4DiskLocation OBJECT-TYPE
			SYNTAX DisplayString
			MAX-ACCESS read-only
			STATUS current
			DESCRIPTION
				"Get the disk location."
			::= { blade4DiskEntry 6 }
		
		blade4SecretKvmVmmTable OBJECT-TYPE
			SYNTAX SEQUENCE OF Blade4SecretKvmVmmEntry
			MAX-ACCESS not-accessible
			STATUS current
			DESCRIPTION
				"A table containing the list of Blade4 KVM&VMM secret information."
			::= { blade4 2010 }

		blade4SecretKvmVmmEntry OBJECT-TYPE
			SYNTAX Blade4SecretKvmVmmEntry
			MAX-ACCESS not-accessible
			STATUS current
			DESCRIPTION
				"Information about a particular current KVM&VMM."
			INDEX { b4SecretKvmVmmIndex }
			::= { blade4SecretKvmVmmTable 1 }
		Blade4SecretKvmVmmEntry ::=
			SEQUENCE { 
				b4SecretKvmVmmIndex
					INTEGER,
				b4SecretKvmState
					INTEGER,
				b4SecretVmmState
					INTEGER,
				b4MMSecretVmmKey
					DisplayString,
				b4SecretVmmKey
					DisplayString
			 }
		b4SecretKvmVmmIndex OBJECT-TYPE
			SYNTAX INTEGER
			MAX-ACCESS not-accessible
			STATUS current
			DESCRIPTION
				"KVM&VMM INDEX."
			::= { blade4SecretKvmVmmEntry 1 }
		b4SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade4SecretKvmVmmEntry 2 }
		b4SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade4SecretKvmVmmEntry 3 }
		b4MMSecretVmmKey OBJECT-TYPE
			SYNTAX DisplayString
			MAX-ACCESS read-only
			STATUS current
			DESCRIPTION
				"Get the MM secret VMM key."
			::= { blade4SecretKvmVmmEntry 4 }
		b4SecretVmmKey OBJECT-TYPE
			SYNTAX DisplayString
			MAX-ACCESS read-write
			STATUS current
			DESCRIPTION
				"Set the secret VMM key."
			::= { blade4SecretKvmVmmEntry 5 }
		blade5 OBJECT IDENTIFIER ::= { blades 5 }

		
 		b5DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade5 4 }
		
 		b5PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade5 5 }
		
 		b5Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade5 6 }

		
 		b5Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b5Health information about a particular b5Location. 
				This will be one of the following:
				(0-ok, 1-minor, 2-major, 3-majorandminor,4-critical,5-criticalandminor,6-criticalandmajor,7-criticalandmajorandminor)"
			::= { blade5 8 }
		
 		b5HealthEvents OBJECT-TYPE
			SYNTAX DisplayString
			MAX-ACCESS read-only
			STATUS current
			DESCRIPTION
				"Events that contribute to the b5Health of the b5Location.  
				This is a list of events currently happening on the 
				b5Location."
			::= { blade5 9 }
		
 		b5ClearSEL OBJECT-TYPE
			SYNTAX INTEGER { clear(1) }
			MAX-ACCESS read-write
			STATUS current
			DESCRIPTION
				"Clean the BMC's SEL on the board."
			::= { blade5 12 }
		
 		b5ExDiskBoardPresence OBJECT-TYPE
			SYNTAX INTEGER
				{
				not-present(0),
				present(1)
				}
			MAX-ACCESS read-only
			STATUS current
			DESCRIPTION
				"Used to find out if the extended disk board is present.
				0 - not present
				1 - present"
			::= { blade5 14 }
		
 		b5BladeVersion OBJECT-TYPE
			SYNTAX DisplayString
			MAX-ACCESS read-only
			STATUS current
			DESCRIPTION
				"display the Version of board5."
			::= { blade5 20 }
		
 		b5MACAddress OBJECT-TYPE
			SYNTAX DisplayString
			MAX-ACCESS read-only
			STATUS current
			DESCRIPTION
				"display the MACAddress of board5."
			::= { blade5 21 }
		
				
							
		
 		b5Safepwofftime OBJECT-TYPE
			SYNTAX INTEGER
			MAX-ACCESS read-write
			STATUS current
			DESCRIPTION
				"the safe poweroff time.
				"
			::= { blade5 26 }
		
 		b5BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]   
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade5 32 }
		
 		b5Systeminfo OBJECT-TYPE
			SYNTAX DisplayString
			MAX-ACCESS read-write
			STATUS current
			DESCRIPTION
				"display the system information of board5."
			::= { blade5 36 }

		
 		b5SystemProperties OBJECT-TYPE
			SYNTAX DisplayString
			MAX-ACCESS read-only
			STATUS current
			DESCRIPTION
				"Get the power of blade1."
			::= { blade5 39 }
		
 		b5BiosCfg OBJECT-TYPE
			SYNTAX DisplayString
			MAX-ACCESS read-write
			STATUS current
			DESCRIPTION
				"Get the power of blade1."
			::= { blade5 40 }
		
 		b5WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade5 41 }
		
 		b5RealTimePower OBJECT-TYPE
			SYNTAX INTEGER
			MAX-ACCESS read-only
			STATUS current
			DESCRIPTION
				" "
			::= { blade5 43 }
		
 		b5PowerCapping OBJECT-TYPE
			SYNTAX DisplayString
			MAX-ACCESS read-write
			STATUS current
			DESCRIPTION
				" "
			::= { blade5 44 }
		
 		b5Powerreference OBJECT-TYPE
			SYNTAX INTEGER
			MAX-ACCESS read-only
			STATUS current
			DESCRIPTION
				" "
			::= { blade5 45 }
		
 		b5ClearBiosConfig OBJECT-TYPE
			SYNTAX INTEGER
			MAX-ACCESS read-write
			STATUS current
			DESCRIPTION
				" "
			::= { blade5 46 }
		
 		b5BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade5 47 }
		
 		b5BmcUserAdd OBJECT-TYPE
			SYNTAX DisplayString
			MAX-ACCESS read-write
			STATUS current
			DESCRIPTION
				"Used to Add the BMC User
				settable format:
				username,passwd"
			::= { blade5 48 }
		
 		b5BmcUserDel OBJECT-TYPE
			SYNTAX DisplayString
			MAX-ACCESS read-write
			STATUS current
			DESCRIPTION
				"Used to Del the BMC User
				settable format:
				username"
			::= { blade5 49 }
		
 		b5BmcUserPasswd OBJECT-TYPE
			SYNTAX DisplayString
			MAX-ACCESS read-write
			STATUS current
			DESCRIPTION
				"Used to Change the BMC User Passwd
				settable format:
				username,passwd"
			::= { blade5 50 }
		
 		b5BmcUserpropertychg OBJECT-TYPE
			SYNTAX DisplayString
			MAX-ACCESS read-write
			STATUS current
			DESCRIPTION
				"Used to Change the BMC User Property
				settable format:
				username,property"
			::= { blade5 51 }
		
 		b5BmcGateway OBJECT-TYPE
			SYNTAX DisplayString
			MAX-ACCESS read-write
			STATUS current
			DESCRIPTION
				"Read or set the gateway."
			::= { blade5 52 }
		
 		b5SlotBitmap OBJECT-TYPE
			SYNTAX INTEGER
			MAX-ACCESS read-only
			STATUS current
			DESCRIPTION
				" "
			::= { blade5 55 }
		
		b5systemGuid OBJECT-TYPE
			SYNTAX DisplayString
			MAX-ACCESS read-only
			STATUS current
			DESCRIPTION
				" "
			::= { blade5 56 }
		
		b5ProductName OBJECT-TYPE
			SYNTAX DisplayString
			MAX-ACCESS read-only
			STATUS current
			DESCRIPTION
				"display the Version of board5."
			::= { blade5 57 }

		b5BundleVersion OBJECT-TYPE
			SYNTAX DisplayString
			MAX-ACCESS read-write
			STATUS current
			DESCRIPTION
				"Get or set the board5 bundle version."
			::= { blade5 58 }

 		blade5SensorTargetTable OBJECT-TYPE
			SYNTAX SEQUENCE OF Blade5SensorTargetEntry
			MAX-ACCESS not-accessible
			STATUS current
			DESCRIPTION
				"A table containing the list of sensor information."
			::= { blade5 2001 }
		
 		blade5SensorTargetEntry OBJECT-TYPE
			SYNTAX Blade5SensorTargetEntry
			MAX-ACCESS not-accessible
			STATUS current
			DESCRIPTION
				"Information about a particular current sensor."
			INDEX { b5Target }
			::= { blade5SensorTargetTable 1 }
		
		Blade5SensorTargetEntry ::=
			SEQUENCE { 
				b5Target
					DisplayString,
				b5Current
					DisplayString,
				b5ThresholdsAll
					DisplayString,
				b5UpperCritical
					DisplayString,
				b5UpperNonCritical
					DisplayString,
				b5UpperNonRecoverable
					DisplayString,
				b5LowerNonCritical
					DisplayString,
				b5LowerCritical
					DisplayString,
				b5LowerNonRecoverable
					DisplayString,
				b5SensorHealth
					INTEGER,
				b5SensorHealthEvents
					DisplayString,
				b5NegativeHysteresis
					DisplayString,
				b5PositiveHysteresis
					DisplayString,
				b5SensorType
					DisplayString,
				b5SensorFRUInfo
					DisplayString
			 }

 		b5Target OBJECT-TYPE
			SYNTAX DisplayString
			MAX-ACCESS not-accessible
			STATUS current
			DESCRIPTION
				"sensor Name"
			::= { blade5SensorTargetEntry 1 }
		
 		b5Current OBJECT-TYPE
			SYNTAX DisplayString
			MAX-ACCESS read-only
			STATUS current
			DESCRIPTION
				"Display the current value of a sensor."
			::= { blade5SensorTargetEntry 2 }
		
 		b5ThresholdsAll OBJECT-TYPE
			SYNTAX DisplayString
			MAX-ACCESS read-only
			STATUS current
			DESCRIPTION
				"All thresholds of a sensor"
			::= { blade5SensorTargetEntry 3 }
		
 		b5UpperCritical OBJECT-TYPE
			SYNTAX DisplayString
			MAX-ACCESS read-write
			STATUS current
			DESCRIPTION
				"Upper critical thresholds"
			::= { blade5SensorTargetEntry 4 }
		
 		b5UpperNonCritical OBJECT-TYPE
			SYNTAX DisplayString
			MAX-ACCESS read-write
			STATUS current
			DESCRIPTION
				"Upper non-critical thresholds"
			::= { blade5SensorTargetEntry 5 }
		
 		b5UpperNonRecoverable OBJECT-TYPE
			SYNTAX DisplayString
			MAX-ACCESS read-write
			STATUS current
			DESCRIPTION
				"Upper non-recoverable thresholds"
			::= { blade5SensorTargetEntry 6 }
		
 		b5LowerNonCritical OBJECT-TYPE
			SYNTAX DisplayString
			MAX-ACCESS read-write
			STATUS current
			DESCRIPTION
				"Lower non-critical thresholds"
			::= { blade5SensorTargetEntry 7 }
		
 		b5LowerCritical OBJECT-TYPE
			SYNTAX DisplayString
			MAX-ACCESS read-write
			STATUS current
			DESCRIPTION
				"Lower critical thresholds"
			::= { blade5SensorTargetEntry 8 }
		
 		b5LowerNonRecoverable OBJECT-TYPE
			SYNTAX DisplayString
			MAX-ACCESS read-write
			STATUS current
			DESCRIPTION
				"Lower non-recoverable thresholds"
			::= { blade5SensorTargetEntry 9 }
		
 		b5SensorHealth OBJECT-TYPE
			SYNTAX INTEGER
				{
				ok(0),
				minor(1),
				major(2),
				critical(3)
				}
			MAX-ACCESS read-only
			STATUS current
			DESCRIPTION
				"b5Health information about a particular b5Location. 
				This will be one of the following:
				(0-ok, 1-minor, 2-major, 3-critical)"
			::= { blade5SensorTargetEntry 10 }
		
 		b5SensorHealthEvents OBJECT-TYPE
			SYNTAX DisplayString
			MAX-ACCESS read-only
			STATUS current
			DESCRIPTION
				"Events that contribute to the b5Health of the b5Location.  
				This is a list of events currently happening on the 
				b5Location."
			::= { blade5SensorTargetEntry 11 }
		
		
 		b5NegativeHysteresis OBJECT-TYPE
			SYNTAX DisplayString
			MAX-ACCESS read-write
			STATUS current
			DESCRIPTION
				"Get/Set the negativeHysteresis value."
			::= { blade5SensorTargetEntry 16 }
		
 		b5PositiveHysteresis OBJECT-TYPE
			SYNTAX DisplayString
			MAX-ACCESS read-write
			STATUS current
			DESCRIPTION
				"Get/Set the positiveHysteresis value."
			::= { blade5SensorTargetEntry 17 }
		
 		b5SensorType OBJECT-TYPE
			SYNTAX DisplayString
			MAX-ACCESS read-only
			STATUS current
			DESCRIPTION
				"Get the type of the sensor."
			::= { blade5SensorTargetEntry 18 }
		
 		b5SensorFRUInfo OBJECT-TYPE
			SYNTAX DisplayString
			MAX-ACCESS read-only
			STATUS current
			DESCRIPTION
				"Get the fruinfo of the sensor."
			::= { blade5SensorTargetEntry 19 }
		
 		blade5FruTable OBJECT-TYPE
			SYNTAX SEQUENCE OF Blade5FruEntry
			MAX-ACCESS not-accessible
			STATUS current
			DESCRIPTION
				"A table containing the list of FRU information."
			::= { blade5 2002 }
		
 		blade5FruEntry OBJECT-TYPE
			SYNTAX Blade5FruEntry
			MAX-ACCESS not-accessible
			STATUS current
			DESCRIPTION
				"Information about a particular current FRU."
			INDEX { b5fruNumber }
			::= { blade5FruTable 1 }
		
		Blade5FruEntry ::=
			SEQUENCE { 
				b5fruNumber
					INTEGER,
				b5FruHotSwapState
					DisplayString,
				b5FruLedProperties
					DisplayString,
				b5FRUControl
					INTEGER,
				b5FRULabel
					DisplayString,
				b5ResetReason
					DisplayString
			 }

 		b5fruNumber OBJECT-TYPE
			SYNTAX INTEGER
			MAX-ACCESS not-accessible
			STATUS current
			DESCRIPTION
				" "
			::= { blade5FruEntry 1 }
		
 		b5FruHotSwapState OBJECT-TYPE
			SYNTAX DisplayString
			MAX-ACCESS read-only
			STATUS current
			DESCRIPTION
				"Retrieve the hot swap state of the FRU from the 
				internally known hot swap states of blade5."
			::= { blade5FruEntry 3 }
		
 		b5FruLedProperties OBJECT-TYPE
			SYNTAX DisplayString
			MAX-ACCESS read-only
			STATUS current
			DESCRIPTION
				"Retrieves the LED support information from a FRU. Returns a comma separated
				list of LEDS and the number of FRU supported user LEDs."
			::= { blade5FruEntry 4 }

		

		b5FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade5FruEntry 9 }
		
 		b5FRULabel OBJECT-TYPE
			SYNTAX DisplayString
			MAX-ACCESS read-only
			STATUS current
			DESCRIPTION
				"Get fru label of blade5."
			::= { blade5FruEntry 10 }
		
 		b5ResetReason OBJECT-TYPE
			SYNTAX DisplayString
			MAX-ACCESS read-only
			STATUS current
			DESCRIPTION
				"Delete fru label of smm."
			::= { blade5FruEntry 11 }
		
 		blade5FruLedTable OBJECT-TYPE
			SYNTAX SEQUENCE OF Blade5FruLedEntry
			MAX-ACCESS not-accessible
			STATUS current
			DESCRIPTION
				"A table containing the list of led information."
			::= { blade5 2003 }
		
 		blade5FruLedEntry OBJECT-TYPE
			SYNTAX Blade5FruLedEntry
			MAX-ACCESS not-accessible
			STATUS current
			DESCRIPTION
				"Information about a particular current led."
			INDEX { b5FruID, b5FruLed }
			::= { blade5FruLedTable 1 }
		
		Blade5FruLedEntry ::=
			SEQUENCE { 
				b5FruID
					INTEGER,
				b5FruLed
					DisplayString,
				b5FruLedColorProps
					DisplayString,
				b5FruLedState
					DisplayString
			 }

 		b5FruID OBJECT-TYPE
			SYNTAX INTEGER
			MAX-ACCESS not-accessible
			STATUS current
			DESCRIPTION
				" "
			::= { blade5FruLedEntry 1 }
		
 		b5FruLed OBJECT-TYPE
			SYNTAX DisplayString
			MAX-ACCESS not-accessible
			STATUS current
			DESCRIPTION
				" "
			::= { blade5FruLedEntry 2 }
		
 		b5FruLedColorProps OBJECT-TYPE
			SYNTAX DisplayString
			MAX-ACCESS read-only
			STATUS current
			DESCRIPTION
				"Finds out what colors are supported by the LED"
			::= { blade5FruLedEntry 3 }
		
 		b5FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade5FruLedEntry 4 }
		
 		blade5FruDescriptionTable OBJECT-TYPE
			SYNTAX SEQUENCE OF Blade5FruDescriptionEntry
			MAX-ACCESS not-accessible
			STATUS current
			DESCRIPTION
				"A table containing the list of blade5 FRU information."
			::= { blade5 2004 }
		
 		blade5FruDescriptionEntry OBJECT-TYPE
			SYNTAX Blade5FruDescriptionEntry
			MAX-ACCESS not-accessible
			STATUS current
			DESCRIPTION
				"Information about a particular current FRU."
			INDEX { b5fruNum }
			::= { blade5FruDescriptionTable 1 }
		
		Blade5FruDescriptionEntry ::=
			SEQUENCE { 
				b5fruNum
					INTEGER,
				b5fruBoardDescription
					DisplayString,
				b5fruBoardManufacturer
					DisplayString,
				b5fruBoardPartNumber
					DisplayString,
				b5fruBoardSerialNumber
					DisplayString,
				b5fruBoardManufactureDate
					DisplayString,
				b5fruProductDescription
					DisplayString,
				b5fruProductManufacturer
					DisplayString,
				b5fruProductPartNumber
					DisplayString,
				b5fruProductSerialNumber
					DisplayString,
				b5fruProductRevision
					DisplayString,
				b5fruAll
					DisplayString
			 }

 		b5fruNum OBJECT-TYPE
			SYNTAX INTEGER
			MAX-ACCESS not-accessible
			STATUS current
			DESCRIPTION
				"blade5 FRU's INDEX"
			::= { blade5FruDescriptionEntry 1 }
		
 		b5fruBoardDescription OBJECT-TYPE
			SYNTAX DisplayString
			MAX-ACCESS read-only
			STATUS current
			DESCRIPTION
				"Used to read the Board Description from the blade5 fru."
			::= { blade5FruDescriptionEntry 2 }
		
 		b5fruBoardManufacturer OBJECT-TYPE
			SYNTAX DisplayString
			MAX-ACCESS read-only
			STATUS current
			DESCRIPTION
				"Used to read the Board Manufacturer from the bladef5 fru."
			::= { blade5FruDescriptionEntry 3 }
		
 		b5fruBoardPartNumber OBJECT-TYPE
			SYNTAX DisplayString
			MAX-ACCESS read-only
			STATUS current
			DESCRIPTION
				"Used to read the Board Part Number from the blade5 fru."
			::= { blade5FruDescriptionEntry 4 }
		
 		b5fruBoardSerialNumber OBJECT-TYPE
			SYNTAX DisplayString
			MAX-ACCESS read-only
			STATUS current
			DESCRIPTION
				"Used to read the Board Serial Number from the blade5 fru."
			::= { blade5FruDescriptionEntry 5 }
		
 		b5fruBoardManufactureDate OBJECT-TYPE
			SYNTAX DisplayString
			MAX-ACCESS read-only
			STATUS current
			DESCRIPTION
				"Used to read the Board Manufacture Date from the blade5 fru."
			::= { blade5FruDescriptionEntry 6 }
		
 		b5fruProductDescription OBJECT-TYPE
			SYNTAX DisplayString
			MAX-ACCESS read-only
			STATUS current
			DESCRIPTION
				"Used to read the Product Description from the blade5 fru."
			::= { blade5FruDescriptionEntry 7 }
		
 		b5fruProductManufacturer OBJECT-TYPE
			SYNTAX DisplayString
			MAX-ACCESS read-only
			STATUS current
			DESCRIPTION
				"Used to read the Product Manufacturer from the blade5 fru."
			::= { blade5FruDescriptionEntry 8 }
		
 		b5fruProductPartNumber OBJECT-TYPE
			SYNTAX DisplayString
			MAX-ACCESS read-only
			STATUS current
			DESCRIPTION
				"Used to read the Product Part Number from the blade5 fru."
			::= { blade5FruDescriptionEntry 9 }
		
 		b5fruProductSerialNumber OBJECT-TYPE
			SYNTAX DisplayString
			MAX-ACCESS read-only
			STATUS current
			DESCRIPTION
				"Used to read the Product Serial Number from the blade5 fru."
			::= { blade5FruDescriptionEntry 10 }
		
 		b5fruProductRevision OBJECT-TYPE
			SYNTAX DisplayString
			MAX-ACCESS read-only
			STATUS current
			DESCRIPTION
				"Used to read the Product Revision from the blade5 fru."
			::= { blade5FruDescriptionEntry 13 }
		
 		b5fruAll OBJECT-TYPE
			SYNTAX DisplayString
			MAX-ACCESS read-only
			STATUS current
			DESCRIPTION
				"Used to read the fru info all."
			::= { blade5FruDescriptionEntry 14 }
		
		blade5CPUTable OBJECT-TYPE
			SYNTAX SEQUENCE OF Blade5CPUEntry
			MAX-ACCESS not-accessible
			STATUS current
			DESCRIPTION
				"A table containing the list of Blade1 FRU information."
			::= { blade5 2006 }
		
		blade5CPUEntry OBJECT-TYPE
			SYNTAX Blade5CPUEntry
			MAX-ACCESS not-accessible
			STATUS current
			DESCRIPTION
				"Information about a particular current FRU."
			INDEX { b5CPUIndex }
			::= { blade5CPUTable 1 }
		
		Blade5CPUEntry ::=
			SEQUENCE { 
				b5CPUIndex
					INTEGER,
				b5CPUMark
					DisplayString,
				b5CPUInfo
					DisplayString,
				b5CPUPresent
					INTEGER,
				b5CPUHealth
					INTEGER,
				b5CPULocation
					DisplayString
			 }

		b5CPUIndex OBJECT-TYPE
			SYNTAX INTEGER
			MAX-ACCESS not-accessible
			STATUS current
			DESCRIPTION
				"CPU INDEX"
			::= { blade5CPUEntry 1 }
		
		b5CPUMark OBJECT-TYPE
			SYNTAX DisplayString
			MAX-ACCESS read-only
			STATUS current
			DESCRIPTION
				"Get the CPU silk-screen."
			::= { blade5CPUEntry 2 }
		
		b5CPUInfo OBJECT-TYPE
			SYNTAX DisplayString
			MAX-ACCESS read-only
			STATUS current
			DESCRIPTION
				"Get the CPU description of vendor, type and frequency."
			::= { blade5CPUEntry 3 }
		
		b5CPUPresent OBJECT-TYPE
			SYNTAX INTEGER
			MAX-ACCESS read-only
			STATUS current
			DESCRIPTION
				"Get the CPU presence status."
			::= { blade5CPUEntry 4 }
		
		b5CPUHealth OBJECT-TYPE
			SYNTAX INTEGER
			MAX-ACCESS read-only
			STATUS current
			DESCRIPTION
				"Get the CPU health status."
			::= { blade5CPUEntry 5 }
		
		b5CPULocation OBJECT-TYPE
			SYNTAX DisplayString
			MAX-ACCESS read-only
			STATUS current
			DESCRIPTION
				"Get the CPU location."
			::= { blade5CPUEntry 6 }
		
		blade5MemoryTable OBJECT-TYPE
			SYNTAX SEQUENCE OF Blade5MemoryEntry
			MAX-ACCESS not-accessible
			STATUS current
			DESCRIPTION
				"A table containing the list of Blade1 FRU information."
			::= { blade5 2007 }
		
		blade5MemoryEntry OBJECT-TYPE
			SYNTAX Blade5MemoryEntry
			MAX-ACCESS not-accessible
			STATUS current
			DESCRIPTION
				"Information about a particular current FRU."
			INDEX { b5MEMIndex }
			::= { blade5MemoryTable 1 }
		
		Blade5MemoryEntry ::=
			SEQUENCE { 
				b5MEMIndex
					INTEGER,
				b5MEMMark
					DisplayString,
				b5MEMInfo
					DisplayString,
				b5MEMPresent
					INTEGER,
				b5MEMHealth
					INTEGER,
				b5MEMLocation
					DisplayString
			 }

		b5MEMIndex OBJECT-TYPE
			SYNTAX INTEGER
			MAX-ACCESS not-accessible
			STATUS current
			DESCRIPTION
				"MEMORY INDEX"
			::= { blade5MemoryEntry 1 }
		
		b5MEMMark OBJECT-TYPE
			SYNTAX DisplayString
			MAX-ACCESS read-only
			STATUS current
			DESCRIPTION
				"Get the memory silk-screen."
			::= { blade5MemoryEntry 2 }
		
		b5MEMInfo OBJECT-TYPE
			SYNTAX DisplayString
			MAX-ACCESS read-only
			STATUS current
			DESCRIPTION
				"Get the memory description of vendor, frequency and capacity."
			::= { blade5MemoryEntry 3 }
		
		b5MEMPresent OBJECT-TYPE
			SYNTAX INTEGER
			MAX-ACCESS read-only
			STATUS current
			DESCRIPTION
				"Get the memory presence status."
			::= { blade5MemoryEntry 4 }
		
		b5MEMHealth OBJECT-TYPE
			SYNTAX INTEGER
			MAX-ACCESS read-only
			STATUS current
			DESCRIPTION
				"Get the memory health status."
			::= { blade5MemoryEntry 5 }
		
		b5MEMLocation OBJECT-TYPE
			SYNTAX DisplayString
			MAX-ACCESS read-only
			STATUS current
			DESCRIPTION
				"Get the memory location."
			::= { blade5MemoryEntry 6 }
		
		blade5MezzTable OBJECT-TYPE
			SYNTAX SEQUENCE OF Blade5MezzEntry
			MAX-ACCESS not-accessible
			STATUS current
			DESCRIPTION
				"A table containing the list of Blade1 FRU information."
			::= { blade5 2008 }
		
		blade5MezzEntry OBJECT-TYPE
			SYNTAX Blade5MezzEntry
			MAX-ACCESS not-accessible
			STATUS current
			DESCRIPTION
				"Information about a particular current FRU."
			INDEX { b5MezzIndex }
			::= { blade5MezzTable 1 }
		
		Blade5MezzEntry ::=
			SEQUENCE { 
				b5MezzIndex
					INTEGER,
				b5MezzMark
					DisplayString,
				b5MezzInfo
					DisplayString,
				b5MezzPresent
					INTEGER,
				b5MezzHealth
					INTEGER,
				b5MezzLocation
					DisplayString,
				b5MezzMac
					DisplayString
			 }

		b5MezzIndex OBJECT-TYPE
			SYNTAX INTEGER
			MAX-ACCESS not-accessible
			STATUS current
			DESCRIPTION
				"MEZZ INDEX"
			::= { blade5MezzEntry 1 }
		
		b5MezzMark OBJECT-TYPE
			SYNTAX DisplayString
			MAX-ACCESS read-only
			STATUS current
			DESCRIPTION
				"Get the MEZZ silk-screen."
			::= { blade5MezzEntry 2 }
		
		b5MezzInfo OBJECT-TYPE
			SYNTAX DisplayString
			MAX-ACCESS read-only
			STATUS current
			DESCRIPTION
				"Get the MEZZ description of type."
			::= { blade5MezzEntry 3 }
		
		b5MezzPresent OBJECT-TYPE
			SYNTAX INTEGER
			MAX-ACCESS read-only
			STATUS current
			DESCRIPTION
				"Get the MEZZ presence status."
			::= { blade5MezzEntry 4 }
		
		b5MezzHealth OBJECT-TYPE
			SYNTAX INTEGER
			MAX-ACCESS read-only
			STATUS current
			DESCRIPTION
				"Get the MEZZ health status."
			::= { blade5MezzEntry 5 }
		
		b5MezzLocation OBJECT-TYPE
			SYNTAX DisplayString
			MAX-ACCESS read-only
			STATUS current
			DESCRIPTION
				"Get the MEZZ location."
			::= { blade5MezzEntry 6 }
		
		b5MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade5MezzEntry 7 }
		
		blade5DiskTable OBJECT-TYPE
			SYNTAX SEQUENCE OF Blade5DiskEntry
			MAX-ACCESS not-accessible
			STATUS current
			DESCRIPTION
				"A table containing the list of Blade1 FRU information."
			::= { blade5 2009 }
		
		blade5DiskEntry OBJECT-TYPE
			SYNTAX Blade5DiskEntry
			MAX-ACCESS not-accessible
			STATUS current
			DESCRIPTION
				"Information about a particular current FRU."
			INDEX { b5DiskIndex }
			::= { blade5DiskTable 1 }
		
		Blade5DiskEntry ::=
			SEQUENCE { 
				b5DiskIndex
					INTEGER,
				b5DiskMark
					DisplayString,
				b5DiskInfo
					DisplayString,
				b5DiskPresent
					INTEGER,
				b5DiskHealth
					INTEGER,
				b5DiskLocation
					DisplayString
			 }

		b5DiskIndex OBJECT-TYPE
			SYNTAX INTEGER
			MAX-ACCESS not-accessible
			STATUS current
			DESCRIPTION
				"DISK INDEX"
			::= { blade5DiskEntry 1 }
		
		b5DiskMark OBJECT-TYPE
			SYNTAX DisplayString
			MAX-ACCESS read-only
			STATUS current
			DESCRIPTION
				"Get the disk silk-screen."
			::= { blade5DiskEntry 2 }
		
		b5DiskInfo OBJECT-TYPE
			SYNTAX DisplayString
			MAX-ACCESS read-only
			STATUS current
			DESCRIPTION
				"Get the disk description of vendor, capacity and speed."
			::= { blade5DiskEntry 3 }
		
		b5DiskPresent OBJECT-TYPE
			SYNTAX INTEGER
			MAX-ACCESS read-only
			STATUS current
			DESCRIPTION
				"Get the disk presence status."
			::= { blade5DiskEntry 4 }
		
		b5DiskHealth OBJECT-TYPE
			SYNTAX INTEGER
			MAX-ACCESS read-only
			STATUS current
			DESCRIPTION
				"Get the disk health status."
			::= { blade5DiskEntry 5 }
		
		b5DiskLocation OBJECT-TYPE
			SYNTAX DisplayString
			MAX-ACCESS read-only
			STATUS current
			DESCRIPTION
				"Get the disk location."
			::= { blade5DiskEntry 6 }
		
		blade5SecretKvmVmmTable OBJECT-TYPE
			SYNTAX SEQUENCE OF Blade5SecretKvmVmmEntry
			MAX-ACCESS not-accessible
			STATUS current
			DESCRIPTION
				"A table containing the list of Blade5 KVM&VMM secret information."
			::= { blade5 2010 }

		blade5SecretKvmVmmEntry OBJECT-TYPE
			SYNTAX Blade5SecretKvmVmmEntry
			MAX-ACCESS not-accessible
			STATUS current
			DESCRIPTION
				"Information about a particular current KVM&VMM."
			INDEX { b5SecretKvmVmmIndex }
			::= { blade5SecretKvmVmmTable 1 }
		Blade5SecretKvmVmmEntry ::=
			SEQUENCE { 
				b5SecretKvmVmmIndex
					INTEGER,
				b5SecretKvmState
					INTEGER,
				b5SecretVmmState
					INTEGER,
				b5MMSecretVmmKey
					DisplayString,
				b5SecretVmmKey
					DisplayString
			 }
		b5SecretKvmVmmIndex OBJECT-TYPE
			SYNTAX INTEGER
			MAX-ACCESS not-accessible
			STATUS current
			DESCRIPTION
				"KVM&VMM INDEX."
			::= { blade5SecretKvmVmmEntry 1 }
		b5SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade5SecretKvmVmmEntry 2 }
		b5SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade5SecretKvmVmmEntry 3 }
		b5MMSecretVmmKey OBJECT-TYPE
			SYNTAX DisplayString
			MAX-ACCESS read-only
			STATUS current
			DESCRIPTION
				"Get the MM secret VMM key."
			::= { blade5SecretKvmVmmEntry 4 }
		b5SecretVmmKey OBJECT-TYPE
			SYNTAX DisplayString
			MAX-ACCESS read-write
			STATUS current
			DESCRIPTION
				"Set the secret VMM key."
			::= { blade5SecretKvmVmmEntry 5 }
		blade6 OBJECT IDENTIFIER ::= { blades 6 }

		
 		b6DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade6 4 }
		
 		b6PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade6 5 }
		
 		b6Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade6 6 }

		
 		b6Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b6Health information about a particular b6Location. 
				This will be one of the following:
				(0-ok, 1-minor, 2-major, 3-majorandminor,4-critical,5-criticalandminor,6-criticalandmajor,7-criticalandmajorandminor)"
			::= { blade6 8 }
		
 		b6HealthEvents OBJECT-TYPE
			SYNTAX DisplayString
			MAX-ACCESS read-only
			STATUS current
			DESCRIPTION
				"Events that contribute to the b6Health of the b6Location.  
				This is a list of events currently happening on the 
				b6Location."
			::= { blade6 9 }
		
 		b6ClearSEL OBJECT-TYPE
			SYNTAX INTEGER { clear(1) }
			MAX-ACCESS read-write
			STATUS current
			DESCRIPTION
				"Clean the BMC's SEL on the board."
			::= { blade6 12 }
		
 		b6ExDiskBoardPresence OBJECT-TYPE
			SYNTAX INTEGER
				{
				not-present(0),
				present(1)
				}
			MAX-ACCESS read-only
			STATUS current
			DESCRIPTION
				"Used to find out if the extended disk board is present.
				0 - not present
				1 - present"
			::= { blade6 14 }
		
 		b6BladeVersion OBJECT-TYPE
			SYNTAX DisplayString
			MAX-ACCESS read-only
			STATUS current
			DESCRIPTION
				"display the Version of board6."
			::= { blade6 20 }
		
 		b6MACAddress OBJECT-TYPE
			SYNTAX DisplayString
			MAX-ACCESS read-only
			STATUS current
			DESCRIPTION
				"display the MACAddress of board6."
			::= { blade6 21 }
		
				
							
		
 		b6Safepwofftime OBJECT-TYPE
			SYNTAX INTEGER
			MAX-ACCESS read-write
			STATUS current
			DESCRIPTION
				"the safe poweroff time.
				"
			::= { blade6 26 }
		
 		b6BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade6 32 }
		
 		b6Systeminfo OBJECT-TYPE
			SYNTAX DisplayString
			MAX-ACCESS read-write
			STATUS current
			DESCRIPTION
				"display the system information of board6."
			::= { blade6 36 }

		
 		b6SystemProperties OBJECT-TYPE
			SYNTAX DisplayString
			MAX-ACCESS read-only
			STATUS current
			DESCRIPTION
				"Get the power of blade1."
			::= { blade6 39 }
		
 		b6BiosCfg OBJECT-TYPE
			SYNTAX DisplayString
			MAX-ACCESS read-write
			STATUS current
			DESCRIPTION
				"Get the power of blade1."
			::= { blade6 40 }
		
 		b6WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade6 41 }
		
 		b6RealTimePower OBJECT-TYPE
			SYNTAX INTEGER
			MAX-ACCESS read-only
			STATUS current
			DESCRIPTION
				" "
			::= { blade6 43 }
		
 		b6PowerCapping OBJECT-TYPE
			SYNTAX DisplayString
			MAX-ACCESS read-write
			STATUS current
			DESCRIPTION
				" "
			::= { blade6 44 }
		
 		b6Powerreference OBJECT-TYPE
			SYNTAX INTEGER
			MAX-ACCESS read-only
			STATUS current
			DESCRIPTION
				" "
			::= { blade6 45 }
		
 		b6ClearBiosConfig OBJECT-TYPE
			SYNTAX INTEGER
			MAX-ACCESS read-write
			STATUS current
			DESCRIPTION
				" "
			::= { blade6 46 }
		
 		b6BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade6 47 }
		
 		b6BmcUserAdd OBJECT-TYPE
			SYNTAX DisplayString
			MAX-ACCESS read-write
			STATUS current
			DESCRIPTION
				"Used to Add the BMC User
				settable format:
				username,passwd"
			::= { blade6 48 }
		
 		b6BmcUserDel OBJECT-TYPE
			SYNTAX DisplayString
			MAX-ACCESS read-write
			STATUS current
			DESCRIPTION
				"Used to Del the BMC User
				settable format:
				username"
			::= { blade6 49 }
		
 		b6BmcUserPasswd OBJECT-TYPE
			SYNTAX DisplayString
			MAX-ACCESS read-write
			STATUS current
			DESCRIPTION
				"Used to Change the BMC User Passwd
				settable format:
				username,passwd"
			::= { blade6 50 }
		
 		b6BmcUserpropertychg OBJECT-TYPE
			SYNTAX DisplayString
			MAX-ACCESS read-write
			STATUS current
			DESCRIPTION
				"Used to Change the BMC User Property
				settable format:
				username,property"
			::= { blade6 51 }
		
 		b6BmcGateway OBJECT-TYPE
			SYNTAX DisplayString
			MAX-ACCESS read-write
			STATUS current
			DESCRIPTION
				"Read or set the gateway."
			::= { blade6 52 }
		
 		b6SlotBitmap OBJECT-TYPE
			SYNTAX INTEGER
			MAX-ACCESS read-only
			STATUS current
			DESCRIPTION
				" "
			::= { blade6 55 }
		
		b6systemGuid OBJECT-TYPE
			SYNTAX DisplayString
			MAX-ACCESS read-only
			STATUS current
			DESCRIPTION
				" "
			::= { blade6 56 }
		
		b6ProductName OBJECT-TYPE
			SYNTAX DisplayString
			MAX-ACCESS read-only
			STATUS current
			DESCRIPTION
				"display the Version of board6."
			::= { blade6 57 }

		b6BundleVersion OBJECT-TYPE
			SYNTAX DisplayString
			MAX-ACCESS read-write
			STATUS current
			DESCRIPTION
				"Get or set the board6 bundle version."
			::= { blade6 58 }

 		blade6SensorTargetTable OBJECT-TYPE
			SYNTAX SEQUENCE OF Blade6SensorTargetEntry
			MAX-ACCESS not-accessible
			STATUS current
			DESCRIPTION
				"A table containing the list of sensor information."
			::= { blade6 2001 }
		
 		blade6SensorTargetEntry OBJECT-TYPE
			SYNTAX Blade6SensorTargetEntry
			MAX-ACCESS not-accessible
			STATUS current
			DESCRIPTION
				"Information about a particular current sensor."
			INDEX { b6Target }
			::= { blade6SensorTargetTable 1 }
		
		Blade6SensorTargetEntry ::=
			SEQUENCE { 
				b6Target
					DisplayString,
				b6Current
					DisplayString,
				b6ThresholdsAll
					DisplayString,
				b6UpperCritical
					DisplayString,
				b6UpperNonCritical
					DisplayString,
				b6UpperNonRecoverable
					DisplayString,
				b6LowerNonCritical
					DisplayString,
				b6LowerCritical
					DisplayString,
				b6LowerNonRecoverable
					DisplayString,
				b6SensorHealth
					INTEGER,
				b6SensorHealthEvents
					DisplayString,
				b6NegativeHysteresis
					DisplayString,
				b6PositiveHysteresis
					DisplayString,
				b6SensorType
					DisplayString,
				b6SensorFRUInfo
					DisplayString
			 }

 		b6Target OBJECT-TYPE
			SYNTAX DisplayString
			MAX-ACCESS not-accessible
			STATUS current
			DESCRIPTION
				"sensor Name"
			::= { blade6SensorTargetEntry 1 }
		
 		b6Current OBJECT-TYPE
			SYNTAX DisplayString
			MAX-ACCESS read-only
			STATUS current
			DESCRIPTION
				"Display the current value of a sensor."
			::= { blade6SensorTargetEntry 2 }
		
 		b6ThresholdsAll OBJECT-TYPE
			SYNTAX DisplayString
			MAX-ACCESS read-only
			STATUS current
			DESCRIPTION
				"All thresholds of a sensor"
			::= { blade6SensorTargetEntry 3 }
		
 		b6UpperCritical OBJECT-TYPE
			SYNTAX DisplayString
			MAX-ACCESS read-write
			STATUS current
			DESCRIPTION
				"Upper critical thresholds"
			::= { blade6SensorTargetEntry 4 }
		
 		b6UpperNonCritical OBJECT-TYPE
			SYNTAX DisplayString
			MAX-ACCESS read-write
			STATUS current
			DESCRIPTION
				"Upper non-critical thresholds"
			::= { blade6SensorTargetEntry 5 }
		
 		b6UpperNonRecoverable OBJECT-TYPE
			SYNTAX DisplayString
			MAX-ACCESS read-write
			STATUS current
			DESCRIPTION
				"Upper non-recoverable thresholds"
			::= { blade6SensorTargetEntry 6 }
		
 		b6LowerNonCritical OBJECT-TYPE
			SYNTAX DisplayString
			MAX-ACCESS read-write
			STATUS current
			DESCRIPTION
				"Lower non-critical thresholds"
			::= { blade6SensorTargetEntry 7 }
		
 		b6LowerCritical OBJECT-TYPE
			SYNTAX DisplayString
			MAX-ACCESS read-write
			STATUS current
			DESCRIPTION
				"Lower critical thresholds"
			::= { blade6SensorTargetEntry 8 }
		
 		b6LowerNonRecoverable OBJECT-TYPE
			SYNTAX DisplayString
			MAX-ACCESS read-write
			STATUS current
			DESCRIPTION
				"Lower non-recoverable thresholds"
			::= { blade6SensorTargetEntry 9 }
		
 		b6SensorHealth OBJECT-TYPE
			SYNTAX INTEGER
				{
				ok(0),
				minor(1),
				major(2),
				critical(3)
				}
			MAX-ACCESS read-only
			STATUS current
			DESCRIPTION
				"b6Health information about a particular b6Location. 
				This will be one of the following:
				(0-ok, 1-minor, 2-major, 3-critical)"
			::= { blade6SensorTargetEntry 10 }
		
 		b6SensorHealthEvents OBJECT-TYPE
			SYNTAX DisplayString
			MAX-ACCESS read-only
			STATUS current
			DESCRIPTION
				"Events that contribute to the b6Health of the b6Location.  
				This is a list of events currently happening on the 
				b6Location."
			::= { blade6SensorTargetEntry 11 }
		
		
 		b6NegativeHysteresis OBJECT-TYPE
			SYNTAX DisplayString
			MAX-ACCESS read-write
			STATUS current
			DESCRIPTION
				"Get/Set the negativeHysteresis value."
			::= { blade6SensorTargetEntry 16 }
		
 		b6PositiveHysteresis OBJECT-TYPE
			SYNTAX DisplayString
			MAX-ACCESS read-write
			STATUS current
			DESCRIPTION
				"Get/Set the positiveHysteresis value."
			::= { blade6SensorTargetEntry 17 }
		
 		b6SensorType OBJECT-TYPE
			SYNTAX DisplayString
			MAX-ACCESS read-only
			STATUS current
			DESCRIPTION
				"Get the type of the sensor."
			::= { blade6SensorTargetEntry 18 }
		
 		b6SensorFRUInfo OBJECT-TYPE
			SYNTAX DisplayString
			MAX-ACCESS read-only
			STATUS current
			DESCRIPTION
				"Get the fruinfo of the sensor."
			::= { blade6SensorTargetEntry 19 }
		
 		blade6FruTable OBJECT-TYPE
			SYNTAX SEQUENCE OF Blade6FruEntry
			MAX-ACCESS not-accessible
			STATUS current
			DESCRIPTION
				"A table containing the list of FRU information."
			::= { blade6 2002 }
		
 		blade6FruEntry OBJECT-TYPE
			SYNTAX Blade6FruEntry
			MAX-ACCESS not-accessible
			STATUS current
			DESCRIPTION
				"Information about a particular current FRU."
			INDEX { b6fruNumber }
			::= { blade6FruTable 1 }
		
		Blade6FruEntry ::=
			SEQUENCE { 
				b6fruNumber
					INTEGER,
				b6FruHotSwapState
					DisplayString,
				b6FruLedProperties
					DisplayString,
				b6FRUControl
					INTEGER,
				b6FRULabel
					DisplayString,
				b6ResetReason
					DisplayString
			 }

 		b6fruNumber OBJECT-TYPE
			SYNTAX INTEGER
			MAX-ACCESS not-accessible
			STATUS current
			DESCRIPTION
				" "
			::= { blade6FruEntry 1 }
		
 		b6FruHotSwapState OBJECT-TYPE
			SYNTAX DisplayString
			MAX-ACCESS read-only
			STATUS current
			DESCRIPTION
				"Retrieve the hot swap state of the FRU from the 
				internally known hot swap states of blade6."
			::= { blade6FruEntry 3 }
		
 		b6FruLedProperties OBJECT-TYPE
			SYNTAX DisplayString
			MAX-ACCESS read-only
			STATUS current
			DESCRIPTION
				"Retrieves the LED support information from a FRU. Returns a comma separated
				list of LEDS and the number of FRU supported user LEDs."
			::= { blade6FruEntry 4 }

		

		b6FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade6FruEntry 9 }
		
 		b6FRULabel OBJECT-TYPE
			SYNTAX DisplayString
			MAX-ACCESS read-only
			STATUS current
			DESCRIPTION
				"Get fru label of blade6."
			::= { blade6FruEntry 10 }
		
 		b6ResetReason OBJECT-TYPE
			SYNTAX DisplayString
			MAX-ACCESS read-only
			STATUS current
			DESCRIPTION
				"Delete fru label of smm."
			::= { blade6FruEntry 11 }
		
 		blade6FruLedTable OBJECT-TYPE
			SYNTAX SEQUENCE OF Blade6FruLedEntry
			MAX-ACCESS not-accessible
			STATUS current
			DESCRIPTION
				"A table containing the list of led information."
			::= { blade6 2003 }
		
 		blade6FruLedEntry OBJECT-TYPE
			SYNTAX Blade6FruLedEntry
			MAX-ACCESS not-accessible
			STATUS current
			DESCRIPTION
				"Information about a particular current led."
			INDEX { b6FruID, b6FruLed }
			::= { blade6FruLedTable 1 }
		
		Blade6FruLedEntry ::=
			SEQUENCE { 
				b6FruID
					INTEGER,
				b6FruLed
					DisplayString,
				b6FruLedColorProps
					DisplayString,
				b6FruLedState
					DisplayString
			 }

 		b6FruID OBJECT-TYPE
			SYNTAX INTEGER
			MAX-ACCESS not-accessible
			STATUS current
			DESCRIPTION
				" "
			::= { blade6FruLedEntry 1 }
		
 		b6FruLed OBJECT-TYPE
			SYNTAX DisplayString
			MAX-ACCESS not-accessible
			STATUS current
			DESCRIPTION
				" "
			::= { blade6FruLedEntry 2 }
		
 		b6FruLedColorProps OBJECT-TYPE
			SYNTAX DisplayString
			MAX-ACCESS read-only
			STATUS current
			DESCRIPTION
				"Finds out what colors are supported by the LED"
			::= { blade6FruLedEntry 3 }
		
 		b6FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade6FruLedEntry 4 }
		
 		blade6FruDescriptionTable OBJECT-TYPE
			SYNTAX SEQUENCE OF Blade6FruDescriptionEntry
			MAX-ACCESS not-accessible
			STATUS current
			DESCRIPTION
				"A table containing the list of blade6 FRU information."
			::= { blade6 2004 }
		
 		blade6FruDescriptionEntry OBJECT-TYPE
			SYNTAX Blade6FruDescriptionEntry
			MAX-ACCESS not-accessible
			STATUS current
			DESCRIPTION
				"Information about a particular current FRU."
			INDEX { b6fruNum }
			::= { blade6FruDescriptionTable 1 }
		
		Blade6FruDescriptionEntry ::=
			SEQUENCE { 
				b6fruNum
					INTEGER,
				b6fruBoardDescription
					DisplayString,
				b6fruBoardManufacturer
					DisplayString,
				b6fruBoardPartNumber
					DisplayString,
				b6fruBoardSerialNumber
					DisplayString,
				b6fruBoardManufactureDate
					DisplayString,
				b6fruProductDescription
					DisplayString,
				b6fruProductManufacturer
					DisplayString,
				b6fruProductPartNumber
					DisplayString,
				b6fruProductSerialNumber
					DisplayString,
				b6fruProductRevision
					DisplayString,
				b6fruAll
					DisplayString
			 }

 		b6fruNum OBJECT-TYPE
			SYNTAX INTEGER
			MAX-ACCESS not-accessible
			STATUS current
			DESCRIPTION
				"blade6 FRU's INDEX"
			::= { blade6FruDescriptionEntry 1 }
		
 		b6fruBoardDescription OBJECT-TYPE
			SYNTAX DisplayString
			MAX-ACCESS read-only
			STATUS current
			DESCRIPTION
				"Used to read the Board Description from the blade6 fru."
			::= { blade6FruDescriptionEntry 2 }
		
 		b6fruBoardManufacturer OBJECT-TYPE
			SYNTAX DisplayString
			MAX-ACCESS read-only
			STATUS current
			DESCRIPTION
				"Used to read the Board Manufacturer from the bladef6 fru."
			::= { blade6FruDescriptionEntry 3 }
		
 		b6fruBoardPartNumber OBJECT-TYPE
			SYNTAX DisplayString
			MAX-ACCESS read-only
			STATUS current
			DESCRIPTION
				"Used to read the Board Part Number from the blade6 fru."
			::= { blade6FruDescriptionEntry 4 }
		
 		b6fruBoardSerialNumber OBJECT-TYPE
			SYNTAX DisplayString
			MAX-ACCESS read-only
			STATUS current
			DESCRIPTION
				"Used to read the Board Serial Number from the blade6 fru."
			::= { blade6FruDescriptionEntry 5 }
		
 		b6fruBoardManufactureDate OBJECT-TYPE
			SYNTAX DisplayString
			MAX-ACCESS read-only
			STATUS current
			DESCRIPTION
				"Used to read the Board Manufacture Date from the blade6 fru."
			::= { blade6FruDescriptionEntry 6 }
		
 		b6fruProductDescription OBJECT-TYPE
			SYNTAX DisplayString
			MAX-ACCESS read-only
			STATUS current
			DESCRIPTION
				"Used to read the Product Description from the blade6 fru."
			::= { blade6FruDescriptionEntry 7 }
		
 		b6fruProductManufacturer OBJECT-TYPE
			SYNTAX DisplayString
			MAX-ACCESS read-only
			STATUS current
			DESCRIPTION
				"Used to read the Product Manufacturer from the blade6 fru."
			::= { blade6FruDescriptionEntry 8 }
		
 		b6fruProductPartNumber OBJECT-TYPE
			SYNTAX DisplayString
			MAX-ACCESS read-only
			STATUS current
			DESCRIPTION
				"Used to read the Product Part Number from the blade6 fru."
			::= { blade6FruDescriptionEntry 9 }
		
 		b6fruProductSerialNumber OBJECT-TYPE
			SYNTAX DisplayString
			MAX-ACCESS read-only
			STATUS current
			DESCRIPTION
				"Used to read the Product Serial Number from the blade6 fru."
			::= { blade6FruDescriptionEntry 10 }
		
 		b6fruProductRevision OBJECT-TYPE
			SYNTAX DisplayString
			MAX-ACCESS read-only
			STATUS current
			DESCRIPTION
				"Used to read the Product Revision from the blade6 fru."
			::= { blade6FruDescriptionEntry 13 }
		
 		b6fruAll OBJECT-TYPE
			SYNTAX DisplayString
			MAX-ACCESS read-only
			STATUS current
			DESCRIPTION
				"Used to read the fru info all."
			::= { blade6FruDescriptionEntry 14 }
		
		blade6CPUTable OBJECT-TYPE
			SYNTAX SEQUENCE OF Blade6CPUEntry
			MAX-ACCESS not-accessible
			STATUS current
			DESCRIPTION
				"A table containing the list of Blade1 FRU information."
			::= { blade6 2006 }
		
		blade6CPUEntry OBJECT-TYPE
			SYNTAX Blade6CPUEntry
			MAX-ACCESS not-accessible
			STATUS current
			DESCRIPTION
				"Information about a particular current FRU."
			INDEX { b6CPUIndex }
			::= { blade6CPUTable 1 }
		
		Blade6CPUEntry ::=
			SEQUENCE { 
				b6CPUIndex
					INTEGER,
				b6CPUMark
					DisplayString,
				b6CPUInfo
					DisplayString,
				b6CPUPresent
					INTEGER,
				b6CPUHealth
					INTEGER,
				b6CPULocation
					DisplayString
			 }

		b6CPUIndex OBJECT-TYPE
			SYNTAX INTEGER
			MAX-ACCESS not-accessible
			STATUS current
			DESCRIPTION
				"CPU INDEX"
			::= { blade6CPUEntry 1 }
		
		b6CPUMark OBJECT-TYPE
			SYNTAX DisplayString
			MAX-ACCESS read-only
			STATUS current
			DESCRIPTION
				"Get the CPU silk-screen."
			::= { blade6CPUEntry 2 }
		
		b6CPUInfo OBJECT-TYPE
			SYNTAX DisplayString
			MAX-ACCESS read-only
			STATUS current
			DESCRIPTION
				"Get the CPU description of vendor, type and frequency."
			::= { blade6CPUEntry 3 }
		
		b6CPUPresent OBJECT-TYPE
			SYNTAX INTEGER
			MAX-ACCESS read-only
			STATUS current
			DESCRIPTION
				"Get the CPU presence status."
			::= { blade6CPUEntry 4 }
		
		b6CPUHealth OBJECT-TYPE
			SYNTAX INTEGER
			MAX-ACCESS read-only
			STATUS current
			DESCRIPTION
				"Get the CPU health status."
			::= { blade6CPUEntry 5 }
		
		b6CPULocation OBJECT-TYPE
			SYNTAX DisplayString
			MAX-ACCESS read-only
			STATUS current
			DESCRIPTION
				"Get the CPU location."
			::= { blade6CPUEntry 6 }
		
		blade6MemoryTable OBJECT-TYPE
			SYNTAX SEQUENCE OF Blade6MemoryEntry
			MAX-ACCESS not-accessible
			STATUS current
			DESCRIPTION
				"A table containing the list of Blade1 FRU information."
			::= { blade6 2007 }
		
		blade6MemoryEntry OBJECT-TYPE
			SYNTAX Blade6MemoryEntry
			MAX-ACCESS not-accessible
			STATUS current
			DESCRIPTION
				"Information about a particular current FRU."
			INDEX { b6MEMIndex }
			::= { blade6MemoryTable 1 }
		
		Blade6MemoryEntry ::=
			SEQUENCE { 
				b6MEMIndex
					INTEGER,
				b6MEMMark
					DisplayString,
				b6MEMInfo
					DisplayString,
				b6MEMPresent
					INTEGER,
				b6MEMHealth
					INTEGER,
				b6MEMLocation
					DisplayString
			 }

		b6MEMIndex OBJECT-TYPE
			SYNTAX INTEGER
			MAX-ACCESS not-accessible
			STATUS current
			DESCRIPTION
				"MEMORY INDEX"
			::= { blade6MemoryEntry 1 }
		
		b6MEMMark OBJECT-TYPE
			SYNTAX DisplayString
			MAX-ACCESS read-only
			STATUS current
			DESCRIPTION
				"Get the memory silk-screen."
			::= { blade6MemoryEntry 2 }
		
		b6MEMInfo OBJECT-TYPE
			SYNTAX DisplayString
			MAX-ACCESS read-only
			STATUS current
			DESCRIPTION
				"Get the memory description of vendor, frequency and capacity."
			::= { blade6MemoryEntry 3 }
		
		b6MEMPresent OBJECT-TYPE
			SYNTAX INTEGER
			MAX-ACCESS read-only
			STATUS current
			DESCRIPTION
				"Get the memory presence status."
			::= { blade6MemoryEntry 4 }
		
		b6MEMHealth OBJECT-TYPE
			SYNTAX INTEGER
			MAX-ACCESS read-only
			STATUS current
			DESCRIPTION
				"Get the memory health status."
			::= { blade6MemoryEntry 5 }
		
		b6MEMLocation OBJECT-TYPE
			SYNTAX DisplayString
			MAX-ACCESS read-only
			STATUS current
			DESCRIPTION
				"Get the memory location."
			::= { blade6MemoryEntry 6 }
		
		blade6MezzTable OBJECT-TYPE
			SYNTAX SEQUENCE OF Blade6MezzEntry
			MAX-ACCESS not-accessible
			STATUS current
			DESCRIPTION
				"A table containing the list of Blade1 FRU information."
			::= { blade6 2008 }
		
		blade6MezzEntry OBJECT-TYPE
			SYNTAX Blade6MezzEntry
			MAX-ACCESS not-accessible
			STATUS current
			DESCRIPTION
				"Information about a particular current FRU."
			INDEX { b6MezzIndex }
			::= { blade6MezzTable 1 }
		
		Blade6MezzEntry ::=
			SEQUENCE { 
				b6MezzIndex
					INTEGER,
				b6MezzMark
					DisplayString,
				b6MezzInfo
					DisplayString,
				b6MezzPresent
					INTEGER,
				b6MezzHealth
					INTEGER,
				b6MezzLocation
					DisplayString,
				b6MezzMac
					DisplayString
			 }

		b6MezzIndex OBJECT-TYPE
			SYNTAX INTEGER
			MAX-ACCESS not-accessible
			STATUS current
			DESCRIPTION
				"MEZZ INDEX"
			::= { blade6MezzEntry 1 }
		
		b6MezzMark OBJECT-TYPE
			SYNTAX DisplayString
			MAX-ACCESS read-only
			STATUS current
			DESCRIPTION
				"Get the MEZZ silk-screen."
			::= { blade6MezzEntry 2 }
		
		b6MezzInfo OBJECT-TYPE
			SYNTAX DisplayString
			MAX-ACCESS read-only
			STATUS current
			DESCRIPTION
				"Get the MEZZ description of type."
			::= { blade6MezzEntry 3 }
		
		b6MezzPresent OBJECT-TYPE
			SYNTAX INTEGER
			MAX-ACCESS read-only
			STATUS current
			DESCRIPTION
				"Get the MEZZ presence status."
			::= { blade6MezzEntry 4 }
		
		b6MezzHealth OBJECT-TYPE
			SYNTAX INTEGER
			MAX-ACCESS read-only
			STATUS current
			DESCRIPTION
				"Get the MEZZ health status."
			::= { blade6MezzEntry 5 }
		
		b6MezzLocation OBJECT-TYPE
			SYNTAX DisplayString
			MAX-ACCESS read-only
			STATUS current
			DESCRIPTION
				"Get the MEZZ location."
			::= { blade6MezzEntry 6 }
		
		b6MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade6MezzEntry 7 }
		
		blade6DiskTable OBJECT-TYPE
			SYNTAX SEQUENCE OF Blade6DiskEntry
			MAX-ACCESS not-accessible
			STATUS current
			DESCRIPTION
				"A table containing the list of Blade1 FRU information."
			::= { blade6 2009 }
		
		blade6DiskEntry OBJECT-TYPE
			SYNTAX Blade6DiskEntry
			MAX-ACCESS not-accessible
			STATUS current
			DESCRIPTION
				"Information about a particular current FRU."
			INDEX { b6DiskIndex }
			::= { blade6DiskTable 1 }
		
		Blade6DiskEntry ::=
			SEQUENCE { 
				b6DiskIndex
					INTEGER,
				b6DiskMark
					DisplayString,
				b6DiskInfo
					DisplayString,
				b6DiskPresent
					INTEGER,
				b6DiskHealth
					INTEGER,
				b6DiskLocation
					DisplayString
			 }

		b6DiskIndex OBJECT-TYPE
			SYNTAX INTEGER
			MAX-ACCESS not-accessible
			STATUS current
			DESCRIPTION
				"DISK INDEX"
			::= { blade6DiskEntry 1 }
		
		b6DiskMark OBJECT-TYPE
			SYNTAX DisplayString
			MAX-ACCESS read-only
			STATUS current
			DESCRIPTION
				"Get the disk silk-screen."
			::= { blade6DiskEntry 2 }
		
		b6DiskInfo OBJECT-TYPE
			SYNTAX DisplayString
			MAX-ACCESS read-only
			STATUS current
			DESCRIPTION
				"Get the disk description of vendor, capacity and speed."
			::= { blade6DiskEntry 3 }
		
		b6DiskPresent OBJECT-TYPE
			SYNTAX INTEGER
			MAX-ACCESS read-only
			STATUS current
			DESCRIPTION
				"Get the disk presence status."
			::= { blade6DiskEntry 4 }
		
		b6DiskHealth OBJECT-TYPE
			SYNTAX INTEGER
			MAX-ACCESS read-only
			STATUS current
			DESCRIPTION
				"Get the disk health status."
			::= { blade6DiskEntry 5 }
		
		b6DiskLocation OBJECT-TYPE
			SYNTAX DisplayString
			MAX-ACCESS read-only
			STATUS current
			DESCRIPTION
				"Get the disk location."
			::= { blade6DiskEntry 6 }
		
		blade6SecretKvmVmmTable OBJECT-TYPE
			SYNTAX SEQUENCE OF Blade6SecretKvmVmmEntry
			MAX-ACCESS not-accessible
			STATUS current
			DESCRIPTION
				"A table containing the list of Blade6 KVM&VMM secret information."
			::= { blade6 2010 }

		blade6SecretKvmVmmEntry OBJECT-TYPE
			SYNTAX Blade6SecretKvmVmmEntry
			MAX-ACCESS not-accessible
			STATUS current
			DESCRIPTION
				"Information about a particular current KVM&VMM."
			INDEX { b6SecretKvmVmmIndex }
			::= { blade6SecretKvmVmmTable 1 }
		Blade6SecretKvmVmmEntry ::=
			SEQUENCE { 
				b6SecretKvmVmmIndex
					INTEGER,
				b6SecretKvmState
					INTEGER,
				b6SecretVmmState
					INTEGER,
				b6MMSecretVmmKey
					DisplayString,
				b6SecretVmmKey
					DisplayString
			 }
		b6SecretKvmVmmIndex OBJECT-TYPE
			SYNTAX INTEGER
			MAX-ACCESS not-accessible
			STATUS current
			DESCRIPTION
				"KVM&VMM INDEX."
			::= { blade6SecretKvmVmmEntry 1 }
		b6SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade6SecretKvmVmmEntry 2 }
		b6SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade6SecretKvmVmmEntry 3 }
		b6MMSecretVmmKey OBJECT-TYPE
			SYNTAX DisplayString
			MAX-ACCESS read-only
			STATUS current
			DESCRIPTION
				"Get the MM secret VMM key."
			::= { blade6SecretKvmVmmEntry 4 }
		b6SecretVmmKey OBJECT-TYPE
			SYNTAX DisplayString
			MAX-ACCESS read-write
			STATUS current
			DESCRIPTION
				"Set the secret VMM key."
			::= { blade6SecretKvmVmmEntry 5 }
		blade7 OBJECT IDENTIFIER ::= { blades 7 }

		
 		b7DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade7 4 }
		
 		b7PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade7 5 }
		
 		b7Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade7 6 }

		
 		b7Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b7Health information about a particular b7Location. 
				This will be one of the following:
				(0-ok, 1-minor, 2-major, 3-majorandminor,4-critical,5-criticalandminor,6-criticalandmajor,7-criticalandmajorandminor)"
			::= { blade7 8 }
		
 		b7HealthEvents OBJECT-TYPE
			SYNTAX DisplayString
			MAX-ACCESS read-only
			STATUS current
			DESCRIPTION
				"Events that contribute to the b7Health of the b7Location.  
				This is a list of events currently happening on the 
				b7Location."
			::= { blade7 9 }
		
 		b7ClearSEL OBJECT-TYPE
			SYNTAX INTEGER { clear(1) }
			MAX-ACCESS read-write
			STATUS current
			DESCRIPTION
				"Clean the BMC's SEL on the board."
			::= { blade7 12 }
		
 		b7ExDiskBoardPresence OBJECT-TYPE
			SYNTAX INTEGER
				{
				not-present(0),
				present(1)
				}
			MAX-ACCESS read-only
			STATUS current
			DESCRIPTION
				"Used to find out if the extended disk board is present.
				0 - not present
				1 - present"
			::= { blade7 14 }
		
 		b7BladeVersion OBJECT-TYPE
			SYNTAX DisplayString
			MAX-ACCESS read-only
			STATUS current
			DESCRIPTION
				"display the Version of board7."
			::= { blade7 20 }
		
 		b7MACAddress OBJECT-TYPE
			SYNTAX DisplayString
			MAX-ACCESS read-only
			STATUS current
			DESCRIPTION
				"display the MACAddress of board7."
			::= { blade7 21 }
		
				
							
		
 		b7Safepwofftime OBJECT-TYPE
			SYNTAX INTEGER
			MAX-ACCESS read-write
			STATUS current
			DESCRIPTION
				"the safe poweroff time.
				"
			::= { blade7 26 }
		
 		b7BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]    
				6=Force boot into BIOS Setup
				15=Force boot from Floppy/primary removable media           
				
				"
			::= { blade7 32 }
		
 		b7Systeminfo OBJECT-TYPE
			SYNTAX DisplayString
			MAX-ACCESS read-write
			STATUS current
			DESCRIPTION
				"display the system information of board7."
			::= { blade7 36 }

		
 		b7SystemProperties OBJECT-TYPE
			SYNTAX DisplayString
			MAX-ACCESS read-only
			STATUS current
			DESCRIPTION
				"Get the power of blade1."
			::= { blade7 39 }
		
 		b7BiosCfg OBJECT-TYPE
			SYNTAX DisplayString
			MAX-ACCESS read-write
			STATUS current
			DESCRIPTION
				"Get the power of blade1."
			::= { blade7 40 }
		
 		b7WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade7 41 }
		
 		b7RealTimePower OBJECT-TYPE
			SYNTAX INTEGER
			MAX-ACCESS read-only
			STATUS current
			DESCRIPTION
				" "
			::= { blade7 43 }
		
 		b7PowerCapping OBJECT-TYPE
			SYNTAX DisplayString
			MAX-ACCESS read-write
			STATUS current
			DESCRIPTION
				" "
			::= { blade7 44 }
		
 		b7Powerreference OBJECT-TYPE
			SYNTAX INTEGER
			MAX-ACCESS read-only
			STATUS current
			DESCRIPTION
				" "
			::= { blade7 45 }
		
 		b7ClearBiosConfig OBJECT-TYPE
			SYNTAX INTEGER
			MAX-ACCESS read-write
			STATUS current
			DESCRIPTION
				" "
			::= { blade7 46 }
		
 		b7BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade7 47 }
		
 		b7BmcUserAdd OBJECT-TYPE
			SYNTAX DisplayString
			MAX-ACCESS read-write
			STATUS current
			DESCRIPTION
				"Used to Add the BMC User
				settable format:
				username,passwd"
			::= { blade7 48 }
		
 		b7BmcUserDel OBJECT-TYPE
			SYNTAX DisplayString
			MAX-ACCESS read-write
			STATUS current
			DESCRIPTION
				"Used to Del the BMC User
				settable format:
				username"
			::= { blade7 49 }
		
 		b7BmcUserPasswd OBJECT-TYPE
			SYNTAX DisplayString
			MAX-ACCESS read-write
			STATUS current
			DESCRIPTION
				"Used to Change the BMC User Passwd
				settable format:
				username,passwd"
			::= { blade7 50 }
		
 		b7BmcUserpropertychg OBJECT-TYPE
			SYNTAX DisplayString
			MAX-ACCESS read-write
			STATUS current
			DESCRIPTION
				"Used to Change the BMC User Property
				settable format:
				username,property"
			::= { blade7 51 }
		
 		b7BmcGateway OBJECT-TYPE
			SYNTAX DisplayString
			MAX-ACCESS read-write
			STATUS current
			DESCRIPTION
				"Read or set the gateway."
			::= { blade7 52 }
		
 		b7SlotBitmap OBJECT-TYPE
			SYNTAX INTEGER
			MAX-ACCESS read-only
			STATUS current
			DESCRIPTION
				" "
			::= { blade7 55 }
		
		b7systemGuid OBJECT-TYPE
			SYNTAX DisplayString
			MAX-ACCESS read-only
			STATUS current
			DESCRIPTION
				" "
			::= { blade7 56 }
		
		b7ProductName OBJECT-TYPE
			SYNTAX DisplayString
			MAX-ACCESS read-only
			STATUS current
			DESCRIPTION
				"display the Version of board7."
			::= { blade7 57 }

		b7BundleVersion OBJECT-TYPE
			SYNTAX DisplayString
			MAX-ACCESS read-write
			STATUS current
			DESCRIPTION
				"Get or set the board7 bundle version."
			::= { blade7 58 }

 		blade7SensorTargetTable OBJECT-TYPE
			SYNTAX SEQUENCE OF Blade7SensorTargetEntry
			MAX-ACCESS not-accessible
			STATUS current
			DESCRIPTION
				"A table containing the list of sensor information."
			::= { blade7 2001 }
		
 		blade7SensorTargetEntry OBJECT-TYPE
			SYNTAX Blade7SensorTargetEntry
			MAX-ACCESS not-accessible
			STATUS current
			DESCRIPTION
				"Information about a particular current sensor."
			INDEX { b7Target }
			::= { blade7SensorTargetTable 1 }
		
		Blade7SensorTargetEntry ::=
			SEQUENCE { 
				b7Target
					DisplayString,
				b7Current
					DisplayString,
				b7ThresholdsAll
					DisplayString,
				b7UpperCritical
					DisplayString,
				b7UpperNonCritical
					DisplayString,
				b7UpperNonRecoverable
					DisplayString,
				b7LowerNonCritical
					DisplayString,
				b7LowerCritical
					DisplayString,
				b7LowerNonRecoverable
					DisplayString,
				b7SensorHealth
					INTEGER,
				b7SensorHealthEvents
					DisplayString,
				b7NegativeHysteresis
					DisplayString,
				b7PositiveHysteresis
					DisplayString,
				b7SensorType
					DisplayString,
				b7SensorFRUInfo
					DisplayString
			 }

 		b7Target OBJECT-TYPE
			SYNTAX DisplayString
			MAX-ACCESS not-accessible
			STATUS current
			DESCRIPTION
				"sensor Name"
			::= { blade7SensorTargetEntry 1 }
		
 		b7Current OBJECT-TYPE
			SYNTAX DisplayString
			MAX-ACCESS read-only
			STATUS current
			DESCRIPTION
				"Display the current value of a sensor."
			::= { blade7SensorTargetEntry 2 }
		
 		b7ThresholdsAll OBJECT-TYPE
			SYNTAX DisplayString
			MAX-ACCESS read-only
			STATUS current
			DESCRIPTION
				"All thresholds of a sensor"
			::= { blade7SensorTargetEntry 3 }
		
 		b7UpperCritical OBJECT-TYPE
			SYNTAX DisplayString
			MAX-ACCESS read-write
			STATUS current
			DESCRIPTION
				"Upper critical thresholds"
			::= { blade7SensorTargetEntry 4 }
		
 		b7UpperNonCritical OBJECT-TYPE
			SYNTAX DisplayString
			MAX-ACCESS read-write
			STATUS current
			DESCRIPTION
				"Upper non-critical thresholds"
			::= { blade7SensorTargetEntry 5 }
		
 		b7UpperNonRecoverable OBJECT-TYPE
			SYNTAX DisplayString
			MAX-ACCESS read-write
			STATUS current
			DESCRIPTION
				"Upper non-recoverable thresholds"
			::= { blade7SensorTargetEntry 6 }
		
 		b7LowerNonCritical OBJECT-TYPE
			SYNTAX DisplayString
			MAX-ACCESS read-write
			STATUS current
			DESCRIPTION
				"Lower non-critical thresholds"
			::= { blade7SensorTargetEntry 7 }
		
 		b7LowerCritical OBJECT-TYPE
			SYNTAX DisplayString
			MAX-ACCESS read-write
			STATUS current
			DESCRIPTION
				"Lower critical thresholds"
			::= { blade7SensorTargetEntry 8 }
		
 		b7LowerNonRecoverable OBJECT-TYPE
			SYNTAX DisplayString
			MAX-ACCESS read-write
			STATUS current
			DESCRIPTION
				"Lower non-recoverable thresholds"
			::= { blade7SensorTargetEntry 9 }
		
 		b7SensorHealth OBJECT-TYPE
			SYNTAX INTEGER
				{
				ok(0),
				minor(1),
				major(2),
				critical(3)
				}
			MAX-ACCESS read-only
			STATUS current
			DESCRIPTION
				"b7Health information about a particular b7Location. 
				This will be one of the following:
				(0-ok, 1-minor, 2-major, 3-critical)"
			::= { blade7SensorTargetEntry 10 }
		
 		b7SensorHealthEvents OBJECT-TYPE
			SYNTAX DisplayString
			MAX-ACCESS read-only
			STATUS current
			DESCRIPTION
				"Events that contribute to the b7Health of the b7Location.  
				This is a list of events currently happening on the 
				b7Location."
			::= { blade7SensorTargetEntry 11 }
		
		
 		b7NegativeHysteresis OBJECT-TYPE
			SYNTAX DisplayString
			MAX-ACCESS read-write
			STATUS current
			DESCRIPTION
				"Get/Set the negativeHysteresis value."
			::= { blade7SensorTargetEntry 16 }
		
 		b7PositiveHysteresis OBJECT-TYPE
			SYNTAX DisplayString
			MAX-ACCESS read-write
			STATUS current
			DESCRIPTION
				"Get/Set the positiveHysteresis value."
			::= { blade7SensorTargetEntry 17 }
		
 		b7SensorType OBJECT-TYPE
			SYNTAX DisplayString
			MAX-ACCESS read-only
			STATUS current
			DESCRIPTION
				"Get the type of the sensor."
			::= { blade7SensorTargetEntry 18 }
		
 		b7SensorFRUInfo OBJECT-TYPE
			SYNTAX DisplayString
			MAX-ACCESS read-only
			STATUS current
			DESCRIPTION
				"Get the fruinfo of the sensor."
			::= { blade7SensorTargetEntry 19 }
		
 		blade7FruTable OBJECT-TYPE
			SYNTAX SEQUENCE OF Blade7FruEntry
			MAX-ACCESS not-accessible
			STATUS current
			DESCRIPTION
				"A table containing the list of FRU information."
			::= { blade7 2002 }
		
 		blade7FruEntry OBJECT-TYPE
			SYNTAX Blade7FruEntry
			MAX-ACCESS not-accessible
			STATUS current
			DESCRIPTION
				"Information about a particular current FRU."
			INDEX { b7fruNumber }
			::= { blade7FruTable 1 }
		
		Blade7FruEntry ::=
			SEQUENCE { 
				b7fruNumber
					INTEGER,
				b7FruHotSwapState
					DisplayString,
				b7FruLedProperties
					DisplayString,
				b7FRUControl
					INTEGER,
				b7FRULabel
					DisplayString,
				b7ResetReason
					DisplayString
			 }

 		b7fruNumber OBJECT-TYPE
			SYNTAX INTEGER
			MAX-ACCESS not-accessible
			STATUS current
			DESCRIPTION
				" "
			::= { blade7FruEntry 1 }
		
 		b7FruHotSwapState OBJECT-TYPE
			SYNTAX DisplayString
			MAX-ACCESS read-only
			STATUS current
			DESCRIPTION
				"Retrieve the hot swap state of the FRU from the 
				internally known hot swap states of blade7."
			::= { blade7FruEntry 3 }
		
 		b7FruLedProperties OBJECT-TYPE
			SYNTAX DisplayString
			MAX-ACCESS read-only
			STATUS current
			DESCRIPTION
				"Retrieves the LED support information from a FRU. Returns a comma separated
				list of LEDS and the number of FRU supported user LEDs."
			::= { blade7FruEntry 4 }

		

		b7FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade7FruEntry 9 }
		
 		b7FRULabel OBJECT-TYPE
			SYNTAX DisplayString
			MAX-ACCESS read-only
			STATUS current
			DESCRIPTION
				"Get fru label of blade7."
			::= { blade7FruEntry 10 }
		
 		b7ResetReason OBJECT-TYPE
			SYNTAX DisplayString
			MAX-ACCESS read-only
			STATUS current
			DESCRIPTION
				"Delete fru label of smm."
			::= { blade7FruEntry 11 }
		
 		blade7FruLedTable OBJECT-TYPE
			SYNTAX SEQUENCE OF Blade7FruLedEntry
			MAX-ACCESS not-accessible
			STATUS current
			DESCRIPTION
				"A table containing the list of led information."
			::= { blade7 2003 }
		
 		blade7FruLedEntry OBJECT-TYPE
			SYNTAX Blade7FruLedEntry
			MAX-ACCESS not-accessible
			STATUS current
			DESCRIPTION
				"Information about a particular current led."
			INDEX { b7FruID, b7FruLed }
			::= { blade7FruLedTable 1 }
		
		Blade7FruLedEntry ::=
			SEQUENCE { 
				b7FruID
					INTEGER,
				b7FruLed
					DisplayString,
				b7FruLedColorProps
					DisplayString,
				b7FruLedState
					DisplayString
			 }

 		b7FruID OBJECT-TYPE
			SYNTAX INTEGER
			MAX-ACCESS not-accessible
			STATUS current
			DESCRIPTION
				" "
			::= { blade7FruLedEntry 1 }
		
 		b7FruLed OBJECT-TYPE
			SYNTAX DisplayString
			MAX-ACCESS not-accessible
			STATUS current
			DESCRIPTION
				" "
			::= { blade7FruLedEntry 2 }
		
 		b7FruLedColorProps OBJECT-TYPE
			SYNTAX DisplayString
			MAX-ACCESS read-only
			STATUS current
			DESCRIPTION
				"Finds out what colors are supported by the LED"
			::= { blade7FruLedEntry 3 }
		
 		b7FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade7FruLedEntry 4 }
		
 		blade7FruDescriptionTable OBJECT-TYPE
			SYNTAX SEQUENCE OF Blade7FruDescriptionEntry
			MAX-ACCESS not-accessible
			STATUS current
			DESCRIPTION
				"A table containing the list of blade7 FRU information."
			::= { blade7 2004 }
		
 		blade7FruDescriptionEntry OBJECT-TYPE
			SYNTAX Blade7FruDescriptionEntry
			MAX-ACCESS not-accessible
			STATUS current
			DESCRIPTION
				"Information about a particular current FRU."
			INDEX { b7fruNum }
			::= { blade7FruDescriptionTable 1 }
		
		Blade7FruDescriptionEntry ::=
			SEQUENCE { 
				b7fruNum
					INTEGER,
				b7fruBoardDescription
					DisplayString,
				b7fruBoardManufacturer
					DisplayString,
				b7fruBoardPartNumber
					DisplayString,
				b7fruBoardSerialNumber
					DisplayString,
				b7fruBoardManufactureDate
					DisplayString,
				b7fruProductDescription
					DisplayString,
				b7fruProductManufacturer
					DisplayString,
				b7fruProductPartNumber
					DisplayString,
				b7fruProductSerialNumber
					DisplayString,
				b7fruProductRevision
					DisplayString,
				b7fruAll
					DisplayString
			 }

 		b7fruNum OBJECT-TYPE
			SYNTAX INTEGER
			MAX-ACCESS not-accessible
			STATUS current
			DESCRIPTION
				"blade7 FRU's INDEX"
			::= { blade7FruDescriptionEntry 1 }
		
 		b7fruBoardDescription OBJECT-TYPE
			SYNTAX DisplayString
			MAX-ACCESS read-only
			STATUS current
			DESCRIPTION
				"Used to read the Board Description from the blade7 fru."
			::= { blade7FruDescriptionEntry 2 }
		
 		b7fruBoardManufacturer OBJECT-TYPE
			SYNTAX DisplayString
			MAX-ACCESS read-only
			STATUS current
			DESCRIPTION
				"Used to read the Board Manufacturer from the bladef7 fru."
			::= { blade7FruDescriptionEntry 3 }
		
 		b7fruBoardPartNumber OBJECT-TYPE
			SYNTAX DisplayString
			MAX-ACCESS read-only
			STATUS current
			DESCRIPTION
				"Used to read the Board Part Number from the blade7 fru."
			::= { blade7FruDescriptionEntry 4 }
		
 		b7fruBoardSerialNumber OBJECT-TYPE
			SYNTAX DisplayString
			MAX-ACCESS read-only
			STATUS current
			DESCRIPTION
				"Used to read the Board Serial Number from the blade7 fru."
			::= { blade7FruDescriptionEntry 5 }
		
 		b7fruBoardManufactureDate OBJECT-TYPE
			SYNTAX DisplayString
			MAX-ACCESS read-only
			STATUS current
			DESCRIPTION
				"Used to read the Board Manufacture Date from the blade7 fru."
			::= { blade7FruDescriptionEntry 6 }
		
 		b7fruProductDescription OBJECT-TYPE
			SYNTAX DisplayString
			MAX-ACCESS read-only
			STATUS current
			DESCRIPTION
				"Used to read the Product Description from the blade7 fru."
			::= { blade7FruDescriptionEntry 7 }
		
 		b7fruProductManufacturer OBJECT-TYPE
			SYNTAX DisplayString
			MAX-ACCESS read-only
			STATUS current
			DESCRIPTION
				"Used to read the Product Manufacturer from the blade7 fru."
			::= { blade7FruDescriptionEntry 8 }
		
 		b7fruProductPartNumber OBJECT-TYPE
			SYNTAX DisplayString
			MAX-ACCESS read-only
			STATUS current
			DESCRIPTION
				"Used to read the Product Part Number from the blade7 fru."
			::= { blade7FruDescriptionEntry 9 }
		
 		b7fruProductSerialNumber OBJECT-TYPE
			SYNTAX DisplayString
			MAX-ACCESS read-only
			STATUS current
			DESCRIPTION
				"Used to read the Product Serial Number from the blade7 fru."
			::= { blade7FruDescriptionEntry 10 }
		
 		b7fruProductRevision OBJECT-TYPE
			SYNTAX DisplayString
			MAX-ACCESS read-only
			STATUS current
			DESCRIPTION
				"Used to read the Product Revision from the blade7 fru."
			::= { blade7FruDescriptionEntry 13 }
		
 		b7fruAll OBJECT-TYPE
			SYNTAX DisplayString
			MAX-ACCESS read-only
			STATUS current
			DESCRIPTION
				"Used to read the fru info all."
			::= { blade7FruDescriptionEntry 14 }
		
		blade7CPUTable OBJECT-TYPE
			SYNTAX SEQUENCE OF Blade7CPUEntry
			MAX-ACCESS not-accessible
			STATUS current
			DESCRIPTION
				"A table containing the list of Blade1 FRU information."
			::= { blade7 2006 }
		
		blade7CPUEntry OBJECT-TYPE
			SYNTAX Blade7CPUEntry
			MAX-ACCESS not-accessible
			STATUS current
			DESCRIPTION
				"Information about a particular current FRU."
			INDEX { b7CPUIndex }
			::= { blade7CPUTable 1 }
		
		Blade7CPUEntry ::=
			SEQUENCE { 
				b7CPUIndex
					INTEGER,
				b7CPUMark
					DisplayString,
				b7CPUInfo
					DisplayString,
				b7CPUPresent
					INTEGER,
				b7CPUHealth
					INTEGER,
				b7CPULocation
					DisplayString
			 }

		b7CPUIndex OBJECT-TYPE
			SYNTAX INTEGER
			MAX-ACCESS not-accessible
			STATUS current
			DESCRIPTION
				"CPU INDEX"
			::= { blade7CPUEntry 1 }
		
		b7CPUMark OBJECT-TYPE
			SYNTAX DisplayString
			MAX-ACCESS read-only
			STATUS current
			DESCRIPTION
				"Get the CPU silk-screen."
			::= { blade7CPUEntry 2 }
		
		b7CPUInfo OBJECT-TYPE
			SYNTAX DisplayString
			MAX-ACCESS read-only
			STATUS current
			DESCRIPTION
				"Get the CPU description of vendor, type and frequency."
			::= { blade7CPUEntry 3 }
		
		b7CPUPresent OBJECT-TYPE
			SYNTAX INTEGER
			MAX-ACCESS read-only
			STATUS current
			DESCRIPTION
				"Get the CPU presence status."
			::= { blade7CPUEntry 4 }
		
		b7CPUHealth OBJECT-TYPE
			SYNTAX INTEGER
			MAX-ACCESS read-only
			STATUS current
			DESCRIPTION
				"Get the CPU health status."
			::= { blade7CPUEntry 5 }
		
		b7CPULocation OBJECT-TYPE
			SYNTAX DisplayString
			MAX-ACCESS read-only
			STATUS current
			DESCRIPTION
				"Get the CPU location."
			::= { blade7CPUEntry 6 }
		
		blade7MemoryTable OBJECT-TYPE
			SYNTAX SEQUENCE OF Blade7MemoryEntry
			MAX-ACCESS not-accessible
			STATUS current
			DESCRIPTION
				"A table containing the list of Blade1 FRU information."
			::= { blade7 2007 }
		
		blade7MemoryEntry OBJECT-TYPE
			SYNTAX Blade7MemoryEntry
			MAX-ACCESS not-accessible
			STATUS current
			DESCRIPTION
				"Information about a particular current FRU."
			INDEX { b7MEMIndex }
			::= { blade7MemoryTable 1 }
		
		Blade7MemoryEntry ::=
			SEQUENCE { 
				b7MEMIndex
					INTEGER,
				b7MEMMark
					DisplayString,
				b7MEMInfo
					DisplayString,
				b7MEMPresent
					INTEGER,
				b7MEMHealth
					INTEGER,
				b7MEMLocation
					DisplayString
			 }

		b7MEMIndex OBJECT-TYPE
			SYNTAX INTEGER
			MAX-ACCESS not-accessible
			STATUS current
			DESCRIPTION
				"MEMORY INDEX"
			::= { blade7MemoryEntry 1 }
		
		b7MEMMark OBJECT-TYPE
			SYNTAX DisplayString
			MAX-ACCESS read-only
			STATUS current
			DESCRIPTION
				"Get the memory silk-screen."
			::= { blade7MemoryEntry 2 }
		
		b7MEMInfo OBJECT-TYPE
			SYNTAX DisplayString
			MAX-ACCESS read-only
			STATUS current
			DESCRIPTION
				"Get the memory description of vendor, frequency and capacity."
			::= { blade7MemoryEntry 3 }
		
		b7MEMPresent OBJECT-TYPE
			SYNTAX INTEGER
			MAX-ACCESS read-only
			STATUS current
			DESCRIPTION
				"Get the memory presence status."
			::= { blade7MemoryEntry 4 }
		
		b7MEMHealth OBJECT-TYPE
			SYNTAX INTEGER
			MAX-ACCESS read-only
			STATUS current
			DESCRIPTION
				"Get the memory health status."
			::= { blade7MemoryEntry 5 }
		
		b7MEMLocation OBJECT-TYPE
			SYNTAX DisplayString
			MAX-ACCESS read-only
			STATUS current
			DESCRIPTION
				"Get the memory location."
			::= { blade7MemoryEntry 6 }
		
		blade7MezzTable OBJECT-TYPE
			SYNTAX SEQUENCE OF Blade7MezzEntry
			MAX-ACCESS not-accessible
			STATUS current
			DESCRIPTION
				"A table containing the list of Blade1 FRU information."
			::= { blade7 2008 }
		
		blade7MezzEntry OBJECT-TYPE
			SYNTAX Blade7MezzEntry
			MAX-ACCESS not-accessible
			STATUS current
			DESCRIPTION
				"Information about a particular current FRU."
			INDEX { b7MezzIndex }
			::= { blade7MezzTable 1 }
		
		Blade7MezzEntry ::=
			SEQUENCE { 
				b7MezzIndex
					INTEGER,
				b7MezzMark
					DisplayString,
				b7MezzInfo
					DisplayString,
				b7MezzPresent
					INTEGER,
				b7MezzHealth
					INTEGER,
				b7MezzLocation
					DisplayString,
				b7MezzMac
					DisplayString
			 }

		b7MezzIndex OBJECT-TYPE
			SYNTAX INTEGER
			MAX-ACCESS not-accessible
			STATUS current
			DESCRIPTION
				"MEZZ INDEX"
			::= { blade7MezzEntry 1 }
		
		b7MezzMark OBJECT-TYPE
			SYNTAX DisplayString
			MAX-ACCESS read-only
			STATUS current
			DESCRIPTION
				"Get the MEZZ silk-screen."
			::= { blade7MezzEntry 2 }
		
		b7MezzInfo OBJECT-TYPE
			SYNTAX DisplayString
			MAX-ACCESS read-only
			STATUS current
			DESCRIPTION
				"Get the MEZZ description of type."
			::= { blade7MezzEntry 3 }
		
		b7MezzPresent OBJECT-TYPE
			SYNTAX INTEGER
			MAX-ACCESS read-only
			STATUS current
			DESCRIPTION
				"Get the MEZZ presence status."
			::= { blade7MezzEntry 4 }
		
		b7MezzHealth OBJECT-TYPE
			SYNTAX INTEGER
			MAX-ACCESS read-only
			STATUS current
			DESCRIPTION
				"Get the MEZZ health status."
			::= { blade7MezzEntry 5 }
		
		b7MezzLocation OBJECT-TYPE
			SYNTAX DisplayString
			MAX-ACCESS read-only
			STATUS current
			DESCRIPTION
				"Get the MEZZ location."
			::= { blade7MezzEntry 6 }
		
		b7MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade7MezzEntry 7 }
		
		blade7DiskTable OBJECT-TYPE
			SYNTAX SEQUENCE OF Blade7DiskEntry
			MAX-ACCESS not-accessible
			STATUS current
			DESCRIPTION
				"A table containing the list of Blade1 FRU information."
			::= { blade7 2009 }
		
		blade7DiskEntry OBJECT-TYPE
			SYNTAX Blade7DiskEntry
			MAX-ACCESS not-accessible
			STATUS current
			DESCRIPTION
				"Information about a particular current FRU."
			INDEX { b7DiskIndex }
			::= { blade7DiskTable 1 }
		
		Blade7DiskEntry ::=
			SEQUENCE { 
				b7DiskIndex
					INTEGER,
				b7DiskMark
					DisplayString,
				b7DiskInfo
					DisplayString,
				b7DiskPresent
					INTEGER,
				b7DiskHealth
					INTEGER,
				b7DiskLocation
					DisplayString
			 }

		b7DiskIndex OBJECT-TYPE
			SYNTAX INTEGER
			MAX-ACCESS not-accessible
			STATUS current
			DESCRIPTION
				"DISK INDEX"
			::= { blade7DiskEntry 1 }
		
		b7DiskMark OBJECT-TYPE
			SYNTAX DisplayString
			MAX-ACCESS read-only
			STATUS current
			DESCRIPTION
				"Get the disk silk-screen."
			::= { blade7DiskEntry 2 }
		
		b7DiskInfo OBJECT-TYPE
			SYNTAX DisplayString
			MAX-ACCESS read-only
			STATUS current
			DESCRIPTION
				"Get the disk description of vendor, capacity and speed."
			::= { blade7DiskEntry 3 }
		
		b7DiskPresent OBJECT-TYPE
			SYNTAX INTEGER
			MAX-ACCESS read-only
			STATUS current
			DESCRIPTION
				"Get the disk presence status."
			::= { blade7DiskEntry 4 }
		
		b7DiskHealth OBJECT-TYPE
			SYNTAX INTEGER
			MAX-ACCESS read-only
			STATUS current
			DESCRIPTION
				"Get the disk health status."
			::= { blade7DiskEntry 5 }
		
		b7DiskLocation OBJECT-TYPE
			SYNTAX DisplayString
			MAX-ACCESS read-only
			STATUS current
			DESCRIPTION
				"Get the disk location."
			::= { blade7DiskEntry 6 }
		
		blade7SecretKvmVmmTable OBJECT-TYPE
			SYNTAX SEQUENCE OF Blade7SecretKvmVmmEntry
			MAX-ACCESS not-accessible
			STATUS current
			DESCRIPTION
				"A table containing the list of Blade7 KVM&VMM secret information."
			::= { blade7 2010 }

		blade7SecretKvmVmmEntry OBJECT-TYPE
			SYNTAX Blade7SecretKvmVmmEntry
			MAX-ACCESS not-accessible
			STATUS current
			DESCRIPTION
				"Information about a particular current KVM&VMM."
			INDEX { b7SecretKvmVmmIndex }
			::= { blade7SecretKvmVmmTable 1 }
		Blade7SecretKvmVmmEntry ::=
			SEQUENCE { 
				b7SecretKvmVmmIndex
					INTEGER,
				b7SecretKvmState
					INTEGER,
				b7SecretVmmState
					INTEGER,
				b7MMSecretVmmKey
					DisplayString,
				b7SecretVmmKey
					DisplayString
			 }
		b7SecretKvmVmmIndex OBJECT-TYPE
			SYNTAX INTEGER
			MAX-ACCESS not-accessible
			STATUS current
			DESCRIPTION
				"KVM&VMM INDEX."
			::= { blade7SecretKvmVmmEntry 1 }
		b7SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade7SecretKvmVmmEntry 2 }
		b7SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade7SecretKvmVmmEntry 3 }
		b7MMSecretVmmKey OBJECT-TYPE
			SYNTAX DisplayString
			MAX-ACCESS read-only
			STATUS current
			DESCRIPTION
				"Get the MM secret VMM key."
			::= { blade7SecretKvmVmmEntry 4 }
		b7SecretVmmKey OBJECT-TYPE
			SYNTAX DisplayString
			MAX-ACCESS read-write
			STATUS current
			DESCRIPTION
				"Set the secret VMM key."
			::= { blade7SecretKvmVmmEntry 5 }
		blade8 OBJECT IDENTIFIER ::= { blades 8 }

		
 		b8DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade8 4 }
		
 		b8PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade8 5 }
		
 		b8Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade8 6 }

		
 		b8Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b8Health information about a particular b8Location. 
				This will be one of the following:
				(0-ok, 1-minor, 2-major, 3-majorandminor,4-critical,5-criticalandminor,6-criticalandmajor,7-criticalandmajorandminor)"
			::= { blade8 8 }
		
 		b8HealthEvents OBJECT-TYPE
			SYNTAX DisplayString
			MAX-ACCESS read-only
			STATUS current
			DESCRIPTION
				"Events that contribute to the b8Health of the b8Location.  
				This is a list of events currently happening on the 
				b8Location."
			::= { blade8 9 }
		
 		b8ClearSEL OBJECT-TYPE
			SYNTAX INTEGER { clear(1) }
			MAX-ACCESS read-write
			STATUS current
			DESCRIPTION
				"Clean the BMC's SEL on the board."
			::= { blade8 12 }
		
 		b8ExDiskBoardPresence OBJECT-TYPE
			SYNTAX INTEGER
				{
				not-present(0),
				present(1)
				}
			MAX-ACCESS read-only
			STATUS current
			DESCRIPTION
				"Used to find out if the extended disk board is present.
				0 - not present
				1 - present"
			::= { blade8 14 }
		
 		b8BladeVersion OBJECT-TYPE
			SYNTAX DisplayString
			MAX-ACCESS read-only
			STATUS current
			DESCRIPTION
				"display the Version of board8."
			::= { blade8 20 }
		
 		b8MACAddress OBJECT-TYPE
			SYNTAX DisplayString
			MAX-ACCESS read-only
			STATUS current
			DESCRIPTION
				"display the MACAddress of board8."
			::= { blade8 21 }
		
				
							
		
 		b8Safepwofftime OBJECT-TYPE
			SYNTAX INTEGER
			MAX-ACCESS read-write
			STATUS current
			DESCRIPTION
				"the safe poweroff time.
				"
			::= { blade8 26 }
		
 		b8BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade8 32 }
		
 		b8Systeminfo OBJECT-TYPE
			SYNTAX DisplayString
			MAX-ACCESS read-write
			STATUS current
			DESCRIPTION
				"display the system information of board8."
			::= { blade8 36 }

		
 		b8SystemProperties OBJECT-TYPE
			SYNTAX DisplayString
			MAX-ACCESS read-only
			STATUS current
			DESCRIPTION
				"Get the power of blade1."
			::= { blade8 39 }
		
 		b8BiosCfg OBJECT-TYPE
			SYNTAX DisplayString
			MAX-ACCESS read-write
			STATUS current
			DESCRIPTION
				"Get the power of blade1."
			::= { blade8 40 }
		
 		b8WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade8 41 }
		
 		b8RealTimePower OBJECT-TYPE
			SYNTAX INTEGER
			MAX-ACCESS read-only
			STATUS current
			DESCRIPTION
				" "
			::= { blade8 43 }
		
 		b8PowerCapping OBJECT-TYPE
			SYNTAX DisplayString
			MAX-ACCESS read-write
			STATUS current
			DESCRIPTION
				" "
			::= { blade8 44 }
		
 		b8Powerreference OBJECT-TYPE
			SYNTAX INTEGER
			MAX-ACCESS read-only
			STATUS current
			DESCRIPTION
				" "
			::= { blade8 45 }
		
 		b8ClearBiosConfig OBJECT-TYPE
			SYNTAX INTEGER
			MAX-ACCESS read-write
			STATUS current
			DESCRIPTION
				" "
			::= { blade8 46 }
		
 		b8BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade8 47 }
		
 		b8BmcUserAdd OBJECT-TYPE
			SYNTAX DisplayString
			MAX-ACCESS read-write
			STATUS current
			DESCRIPTION
				"Used to Add the BMC User
				settable format:
				username,passwd"
			::= { blade8 48 }
		
 		b8BmcUserDel OBJECT-TYPE
			SYNTAX DisplayString
			MAX-ACCESS read-write
			STATUS current
			DESCRIPTION
				"Used to Del the BMC User
				settable format:
				username"
			::= { blade8 49 }
		
 		b8BmcUserPasswd OBJECT-TYPE
			SYNTAX DisplayString
			MAX-ACCESS read-write
			STATUS current
			DESCRIPTION
				"Used to Change the BMC User Passwd
				settable format:
				username,passwd"
			::= { blade8 50 }
		
 		b8BmcUserpropertychg OBJECT-TYPE
			SYNTAX DisplayString
			MAX-ACCESS read-write
			STATUS current
			DESCRIPTION
				"Used to Change the BMC User Property
				settable format:
				username,property"
			::= { blade8 51 }
		
 		b8BmcGateway OBJECT-TYPE
			SYNTAX DisplayString
			MAX-ACCESS read-write
			STATUS current
			DESCRIPTION
				"Read or set the gateway."
			::= { blade8 52 }
		
 		b8SlotBitmap OBJECT-TYPE
			SYNTAX INTEGER
			MAX-ACCESS read-only
			STATUS current
			DESCRIPTION
				" "
			::= { blade8 55 }
		
		b8systemGuid OBJECT-TYPE
			SYNTAX DisplayString
			MAX-ACCESS read-only
			STATUS current
			DESCRIPTION
				" "
			::= { blade8 56 }
		
		b8ProductName OBJECT-TYPE
			SYNTAX DisplayString
			MAX-ACCESS read-only
			STATUS current
			DESCRIPTION
				"display the Version of board8."
			::= { blade8 57 }

		b8BundleVersion OBJECT-TYPE
			SYNTAX DisplayString
			MAX-ACCESS read-write
			STATUS current
			DESCRIPTION
				"Get or set the board8 bundle version."
			::= { blade8 58 }

 		blade8SensorTargetTable OBJECT-TYPE
			SYNTAX SEQUENCE OF Blade8SensorTargetEntry
			MAX-ACCESS not-accessible
			STATUS current
			DESCRIPTION
				"A table containing the list of sensor information."
			::= { blade8 2001 }
		
 		blade8SensorTargetEntry OBJECT-TYPE
			SYNTAX Blade8SensorTargetEntry
			MAX-ACCESS not-accessible
			STATUS current
			DESCRIPTION
				"Information about a particular current sensor."
			INDEX { b8Target }
			::= { blade8SensorTargetTable 1 }
		
		Blade8SensorTargetEntry ::=
			SEQUENCE { 
				b8Target
					DisplayString,
				b8Current
					DisplayString,
				b8ThresholdsAll
					DisplayString,
				b8UpperCritical
					DisplayString,
				b8UpperNonCritical
					DisplayString,
				b8UpperNonRecoverable
					DisplayString,
				b8LowerNonCritical
					DisplayString,
				b8LowerCritical
					DisplayString,
				b8LowerNonRecoverable
					DisplayString,
				b8SensorHealth
					INTEGER,
				b8SensorHealthEvents
					DisplayString,
				b8NegativeHysteresis
					DisplayString,
				b8PositiveHysteresis
					DisplayString,
				b8SensorType
					DisplayString,
				b8SensorFRUInfo
					DisplayString
			 }

 		b8Target OBJECT-TYPE
			SYNTAX DisplayString
			MAX-ACCESS not-accessible
			STATUS current
			DESCRIPTION
				"sensor Name"
			::= { blade8SensorTargetEntry 1 }
		
 		b8Current OBJECT-TYPE
			SYNTAX DisplayString
			MAX-ACCESS read-only
			STATUS current
			DESCRIPTION
				"Display the current value of a sensor."
			::= { blade8SensorTargetEntry 2 }
		
 		b8ThresholdsAll OBJECT-TYPE
			SYNTAX DisplayString
			MAX-ACCESS read-only
			STATUS current
			DESCRIPTION
				"All thresholds of a sensor"
			::= { blade8SensorTargetEntry 3 }
		
 		b8UpperCritical OBJECT-TYPE
			SYNTAX DisplayString
			MAX-ACCESS read-write
			STATUS current
			DESCRIPTION
				"Upper critical thresholds"
			::= { blade8SensorTargetEntry 4 }
		
 		b8UpperNonCritical OBJECT-TYPE
			SYNTAX DisplayString
			MAX-ACCESS read-write
			STATUS current
			DESCRIPTION
				"Upper non-critical thresholds"
			::= { blade8SensorTargetEntry 5 }
		
 		b8UpperNonRecoverable OBJECT-TYPE
			SYNTAX DisplayString
			MAX-ACCESS read-write
			STATUS current
			DESCRIPTION
				"Upper non-recoverable thresholds"
			::= { blade8SensorTargetEntry 6 }
		
 		b8LowerNonCritical OBJECT-TYPE
			SYNTAX DisplayString
			MAX-ACCESS read-write
			STATUS current
			DESCRIPTION
				"Lower non-critical thresholds"
			::= { blade8SensorTargetEntry 7 }
		
 		b8LowerCritical OBJECT-TYPE
			SYNTAX DisplayString
			MAX-ACCESS read-write
			STATUS current
			DESCRIPTION
				"Lower critical thresholds"
			::= { blade8SensorTargetEntry 8 }
		
 		b8LowerNonRecoverable OBJECT-TYPE
			SYNTAX DisplayString
			MAX-ACCESS read-write
			STATUS current
			DESCRIPTION
				"Lower non-recoverable thresholds"
			::= { blade8SensorTargetEntry 9 }
		
 		b8SensorHealth OBJECT-TYPE
			SYNTAX INTEGER
				{
				ok(0),
				minor(1),
				major(2),
				critical(3)
				}
			MAX-ACCESS read-only
			STATUS current
			DESCRIPTION
				"b8Health information about a particular b8Location. 
				This will be one of the following:
				(0-ok, 1-minor, 2-major, 3-critical)"
			::= { blade8SensorTargetEntry 10 }
		
 		b8SensorHealthEvents OBJECT-TYPE
			SYNTAX DisplayString
			MAX-ACCESS read-only
			STATUS current
			DESCRIPTION
				"Events that contribute to the b8Health of the b8Location.  
				This is a list of events currently happening on the 
				b8Location."
			::= { blade8SensorTargetEntry 11 }
		
		
 		b8NegativeHysteresis OBJECT-TYPE
			SYNTAX DisplayString
			MAX-ACCESS read-write
			STATUS current
			DESCRIPTION
				"Get/Set the negativeHysteresis value"
			::= { blade8SensorTargetEntry 16 }
		
 		b8PositiveHysteresis OBJECT-TYPE
			SYNTAX DisplayString
			MAX-ACCESS read-write
			STATUS current
			DESCRIPTION
				"Get/Set the positiveHysteresis value."
			::= { blade8SensorTargetEntry 17 }
		
 		b8SensorType OBJECT-TYPE
			SYNTAX DisplayString
			MAX-ACCESS read-only
			STATUS current
			DESCRIPTION
				"Get the type of the sensor."
			::= { blade8SensorTargetEntry 18 }
		
 		b8SensorFRUInfo OBJECT-TYPE
			SYNTAX DisplayString
			MAX-ACCESS read-only
			STATUS current
			DESCRIPTION
				"Get the fruinfo of the sensor."
			::= { blade8SensorTargetEntry 19 }
		
 		blade8FruTable OBJECT-TYPE
			SYNTAX SEQUENCE OF Blade8FruEntry
			MAX-ACCESS not-accessible
			STATUS current
			DESCRIPTION
				"A table containing the list of FRU information."
			::= { blade8 2002 }
		
 		blade8FruEntry OBJECT-TYPE
			SYNTAX Blade8FruEntry
			MAX-ACCESS not-accessible
			STATUS current
			DESCRIPTION
				"Information about a particular current FRU."
			INDEX { b8fruNumber }
			::= { blade8FruTable 1 }
		
		Blade8FruEntry ::=
			SEQUENCE { 
				b8fruNumber
					INTEGER,
				b8FruHotSwapState
					DisplayString,
				b8FruLedProperties
					DisplayString,
				b8FRUControl
					INTEGER,
				b8FRULabel
					DisplayString,
				b8ResetReason
					DisplayString
			 }

 		b8fruNumber OBJECT-TYPE
			SYNTAX INTEGER
			MAX-ACCESS not-accessible
			STATUS current
			DESCRIPTION
				" "
			::= { blade8FruEntry 1 }
		
 		b8FruHotSwapState OBJECT-TYPE
			SYNTAX DisplayString
			MAX-ACCESS read-only
			STATUS current
			DESCRIPTION
				"Retrieve the hot swap state of the FRU from the 
				internally known hot swap states of blade8."
			::= { blade8FruEntry 3 }
		
 		b8FruLedProperties OBJECT-TYPE
			SYNTAX DisplayString
			MAX-ACCESS read-only
			STATUS current
			DESCRIPTION
				"Retrieves the LED support information from a FRU. Returns a comma separated
				list of LEDS and the number of FRU supported user LEDs."
			::= { blade8FruEntry 4 }

		

		b8FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade8FruEntry 9 }
		
 		b8FRULabel OBJECT-TYPE
			SYNTAX DisplayString
			MAX-ACCESS read-only
			STATUS current
			DESCRIPTION
				"Get fru label of blade8."
			::= { blade8FruEntry 10 }
		
 		b8ResetReason OBJECT-TYPE
			SYNTAX DisplayString
			MAX-ACCESS read-only
			STATUS current
			DESCRIPTION
				"Delete fru label of smm."
			::= { blade8FruEntry 11 }
		
 		blade8FruLedTable OBJECT-TYPE
			SYNTAX SEQUENCE OF Blade8FruLedEntry
			MAX-ACCESS not-accessible
			STATUS current
			DESCRIPTION
				"A table containing the list of led information."
			::= { blade8 2003 }
		
 		blade8FruLedEntry OBJECT-TYPE
			SYNTAX Blade8FruLedEntry
			MAX-ACCESS not-accessible
			STATUS current
			DESCRIPTION
				"Information about a particular current led."
			INDEX { b8FruID, b8FruLed }
			::= { blade8FruLedTable 1 }
		
		Blade8FruLedEntry ::=
			SEQUENCE { 
				b8FruID
					INTEGER,
				b8FruLed
					DisplayString,
				b8FruLedColorProps
					DisplayString,
				b8FruLedState
					DisplayString
			 }

 		b8FruID OBJECT-TYPE
			SYNTAX INTEGER
			MAX-ACCESS not-accessible
			STATUS current
			DESCRIPTION
				" "
			::= { blade8FruLedEntry 1 }
		
 		b8FruLed OBJECT-TYPE
			SYNTAX DisplayString
			MAX-ACCESS not-accessible
			STATUS current
			DESCRIPTION
				" "
			::= { blade8FruLedEntry 2 }
		
 		b8FruLedColorProps OBJECT-TYPE
			SYNTAX DisplayString
			MAX-ACCESS read-only
			STATUS current
			DESCRIPTION
				"Finds out what colors are supported by the LED"
			::= { blade8FruLedEntry 3 }
		
 		b8FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade8FruLedEntry 4 }
		
 		blade8FruDescriptionTable OBJECT-TYPE
			SYNTAX SEQUENCE OF Blade8FruDescriptionEntry
			MAX-ACCESS not-accessible
			STATUS current
			DESCRIPTION
				"A table containing the list of blade8 FRU information."
			::= { blade8 2004 }
		
 		blade8FruDescriptionEntry OBJECT-TYPE
			SYNTAX Blade8FruDescriptionEntry
			MAX-ACCESS not-accessible
			STATUS current
			DESCRIPTION
				"Information about a particular current FRU."
			INDEX { b8fruNum }
			::= { blade8FruDescriptionTable 1 }
		
		Blade8FruDescriptionEntry ::=
			SEQUENCE { 
				b8fruNum
					INTEGER,
				b8fruBoardDescription
					DisplayString,
				b8fruBoardManufacturer
					DisplayString,
				b8fruBoardPartNumber
					DisplayString,
				b8fruBoardSerialNumber
					DisplayString,
				b8fruBoardManufactureDate
					DisplayString,
				b8fruProductDescription
					DisplayString,
				b8fruProductManufacturer
					DisplayString,
				b8fruProductPartNumber
					DisplayString,
				b8fruProductSerialNumber
					DisplayString,
				b8fruProductRevision
					DisplayString,
				b8fruAll
					DisplayString
			 }

 		b8fruNum OBJECT-TYPE
			SYNTAX INTEGER
			MAX-ACCESS not-accessible
			STATUS current
			DESCRIPTION
				"blade8 FRU's INDEX"
			::= { blade8FruDescriptionEntry 1 }
		
 		b8fruBoardDescription OBJECT-TYPE
			SYNTAX DisplayString
			MAX-ACCESS read-only
			STATUS current
			DESCRIPTION
				"Used to read the Board Description from the blade8 fru."
			::= { blade8FruDescriptionEntry 2 }
		
 		b8fruBoardManufacturer OBJECT-TYPE
			SYNTAX DisplayString
			MAX-ACCESS read-only
			STATUS current
			DESCRIPTION
				"Used to read the Board Manufacturer from the bladef8 fru."
			::= { blade8FruDescriptionEntry 3 }
		
 		b8fruBoardPartNumber OBJECT-TYPE
			SYNTAX DisplayString
			MAX-ACCESS read-only
			STATUS current
			DESCRIPTION
				"Used to read the Board Part Number from the blade8 fru."
			::= { blade8FruDescriptionEntry 4 }
		
 		b8fruBoardSerialNumber OBJECT-TYPE
			SYNTAX DisplayString
			MAX-ACCESS read-only
			STATUS current
			DESCRIPTION
				"Used to read the Board Serial Number from the blade8 fru."
			::= { blade8FruDescriptionEntry 5 }
		
 		b8fruBoardManufactureDate OBJECT-TYPE
			SYNTAX DisplayString
			MAX-ACCESS read-only
			STATUS current
			DESCRIPTION
				"Used to read the Board Manufacture Date from the blade8 fru."
			::= { blade8FruDescriptionEntry 6 }
		
 		b8fruProductDescription OBJECT-TYPE
			SYNTAX DisplayString
			MAX-ACCESS read-only
			STATUS current
			DESCRIPTION
				"Used to read the Product Description from the blade8 fru."
			::= { blade8FruDescriptionEntry 7 }
		
 		b8fruProductManufacturer OBJECT-TYPE
			SYNTAX DisplayString
			MAX-ACCESS read-only
			STATUS current
			DESCRIPTION
				"Used to read the Product Manufacturer from the blade8 fru."
			::= { blade8FruDescriptionEntry 8 }
		
 		b8fruProductPartNumber OBJECT-TYPE
			SYNTAX DisplayString
			MAX-ACCESS read-only
			STATUS current
			DESCRIPTION
				"Used to read the Product Part Number from the blade8 fru."
			::= { blade8FruDescriptionEntry 9 }
		
 		b8fruProductSerialNumber OBJECT-TYPE
			SYNTAX DisplayString
			MAX-ACCESS read-only
			STATUS current
			DESCRIPTION
				"Used to read the Product Serial Number from the blade8 fru."
			::= { blade8FruDescriptionEntry 10 }
		
 		b8fruProductRevision OBJECT-TYPE
			SYNTAX DisplayString
			MAX-ACCESS read-only
			STATUS current
			DESCRIPTION
				"Used to read the Product Revision from the blade8 fru."
			::= { blade8FruDescriptionEntry 13 }
		
 		b8fruAll OBJECT-TYPE
			SYNTAX DisplayString
			MAX-ACCESS read-only
			STATUS current
			DESCRIPTION
				"Used to read the fru info all."
			::= { blade8FruDescriptionEntry 14 }
		
		blade8CPUTable OBJECT-TYPE
			SYNTAX SEQUENCE OF Blade8CPUEntry
			MAX-ACCESS not-accessible
			STATUS current
			DESCRIPTION
				"A table containing the list of Blade1 FRU information."
			::= { blade8 2006 }
		
		blade8CPUEntry OBJECT-TYPE
			SYNTAX Blade8CPUEntry
			MAX-ACCESS not-accessible
			STATUS current
			DESCRIPTION
				"Information about a particular current FRU."
			INDEX { b8CPUIndex }
			::= { blade8CPUTable 1 }
		
		Blade8CPUEntry ::=
			SEQUENCE { 
				b8CPUIndex
					INTEGER,
				b8CPUMark
					DisplayString,
				b8CPUInfo
					DisplayString,
				b8CPUPresent
					INTEGER,
				b8CPUHealth
					INTEGER,
				b8CPULocation
					DisplayString
			 }

		b8CPUIndex OBJECT-TYPE
			SYNTAX INTEGER
			MAX-ACCESS not-accessible
			STATUS current
			DESCRIPTION
				"CPU INDEX"
			::= { blade8CPUEntry 1 }
		
		b8CPUMark OBJECT-TYPE
			SYNTAX DisplayString
			MAX-ACCESS read-only
			STATUS current
			DESCRIPTION
				"Get the CPU silk-screen."
			::= { blade8CPUEntry 2 }
		
		b8CPUInfo OBJECT-TYPE
			SYNTAX DisplayString
			MAX-ACCESS read-only
			STATUS current
			DESCRIPTION
				"Get the CPU description of vendor, type and frequency."
			::= { blade8CPUEntry 3 }
		
		b8CPUPresent OBJECT-TYPE
			SYNTAX INTEGER
			MAX-ACCESS read-only
			STATUS current
			DESCRIPTION
				"Get the CPU presence status."
			::= { blade8CPUEntry 4 }
		
		b8CPUHealth OBJECT-TYPE
			SYNTAX INTEGER
			MAX-ACCESS read-only
			STATUS current
			DESCRIPTION
				"Get the CPU health status."
			::= { blade8CPUEntry 5 }
		
		b8CPULocation OBJECT-TYPE
			SYNTAX DisplayString
			MAX-ACCESS read-only
			STATUS current
			DESCRIPTION
				"Get the CPU location."
			::= { blade8CPUEntry 6 }
		
		blade8MemoryTable OBJECT-TYPE
			SYNTAX SEQUENCE OF Blade8MemoryEntry
			MAX-ACCESS not-accessible
			STATUS current
			DESCRIPTION
				"A table containing the list of Blade1 FRU information."
			::= { blade8 2007 }
		
		blade8MemoryEntry OBJECT-TYPE
			SYNTAX Blade8MemoryEntry
			MAX-ACCESS not-accessible
			STATUS current
			DESCRIPTION
				"Information about a particular current FRU."
			INDEX { b8MEMIndex }
			::= { blade8MemoryTable 1 }
		
		Blade8MemoryEntry ::=
			SEQUENCE { 
				b8MEMIndex
					INTEGER,
				b8MEMMark
					DisplayString,
				b8MEMInfo
					DisplayString,
				b8MEMPresent
					INTEGER,
				b8MEMHealth
					INTEGER,
				b8MEMLocation
					DisplayString
			 }

		b8MEMIndex OBJECT-TYPE
			SYNTAX INTEGER
			MAX-ACCESS not-accessible
			STATUS current
			DESCRIPTION
				"MEMORY INDEX"
			::= { blade8MemoryEntry 1 }
		
		b8MEMMark OBJECT-TYPE
			SYNTAX DisplayString
			MAX-ACCESS read-only
			STATUS current
			DESCRIPTION
				"Get the memory silk-screen."
			::= { blade8MemoryEntry 2 }
		
		b8MEMInfo OBJECT-TYPE
			SYNTAX DisplayString
			MAX-ACCESS read-only
			STATUS current
			DESCRIPTION
				"Get the memory description of vendor, frequency and capacity."
			::= { blade8MemoryEntry 3 }
		
		b8MEMPresent OBJECT-TYPE
			SYNTAX INTEGER
			MAX-ACCESS read-only
			STATUS current
			DESCRIPTION
				"Get the memory presence status."
			::= { blade8MemoryEntry 4 }
		
		b8MEMHealth OBJECT-TYPE
			SYNTAX INTEGER
			MAX-ACCESS read-only
			STATUS current
			DESCRIPTION
				"Get the memory health status."
			::= { blade8MemoryEntry 5 }
		
		b8MEMLocation OBJECT-TYPE
			SYNTAX DisplayString
			MAX-ACCESS read-only
			STATUS current
			DESCRIPTION
				"Get the memory location."
			::= { blade8MemoryEntry 6 }
		
		blade8MezzTable OBJECT-TYPE
			SYNTAX SEQUENCE OF Blade8MezzEntry
			MAX-ACCESS not-accessible
			STATUS current
			DESCRIPTION
				"A table containing the list of Blade1 FRU information."
			::= { blade8 2008 }
		
		blade8MezzEntry OBJECT-TYPE
			SYNTAX Blade8MezzEntry
			MAX-ACCESS not-accessible
			STATUS current
			DESCRIPTION
				"Information about a particular current FRU."
			INDEX { b8MezzIndex }
			::= { blade8MezzTable 1 }
		
		Blade8MezzEntry ::=
			SEQUENCE { 
				b8MezzIndex
					INTEGER,
				b8MezzMark
					DisplayString,
				b8MezzInfo
					DisplayString,
				b8MezzPresent
					INTEGER,
				b8MezzHealth
					INTEGER,
				b8MezzLocation
					DisplayString,
				b8MezzMac
					DisplayString
			 }

		b8MezzIndex OBJECT-TYPE
			SYNTAX INTEGER
			MAX-ACCESS not-accessible
			STATUS current
			DESCRIPTION
				"MEZZ INDEX"
			::= { blade8MezzEntry 1 }
		
		b8MezzMark OBJECT-TYPE
			SYNTAX DisplayString
			MAX-ACCESS read-only
			STATUS current
			DESCRIPTION
				"Get the MEZZ silk-screen."
			::= { blade8MezzEntry 2 }
		
		b8MezzInfo OBJECT-TYPE
			SYNTAX DisplayString
			MAX-ACCESS read-only
			STATUS current
			DESCRIPTION
				"Get the MEZZ description of type."
			::= { blade8MezzEntry 3 }
		
		b8MezzPresent OBJECT-TYPE
			SYNTAX INTEGER
			MAX-ACCESS read-only
			STATUS current
			DESCRIPTION
				"Get the MEZZ presence status."
			::= { blade8MezzEntry 4 }
		
		b8MezzHealth OBJECT-TYPE
			SYNTAX INTEGER
			MAX-ACCESS read-only
			STATUS current
			DESCRIPTION
				"Get the MEZZ health status."
			::= { blade8MezzEntry 5 }
		
		b8MezzLocation OBJECT-TYPE
			SYNTAX DisplayString
			MAX-ACCESS read-only
			STATUS current
			DESCRIPTION
				"Get the MEZZ location."
			::= { blade8MezzEntry 6 }
		
		b8MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade8MezzEntry 7 }
		
		blade8DiskTable OBJECT-TYPE
			SYNTAX SEQUENCE OF Blade8DiskEntry
			MAX-ACCESS not-accessible
			STATUS current
			DESCRIPTION
				"A table containing the list of Blade1 FRU information."
			::= { blade8 2009 }
		
		blade8DiskEntry OBJECT-TYPE
			SYNTAX Blade8DiskEntry
			MAX-ACCESS not-accessible
			STATUS current
			DESCRIPTION
				"Information about a particular current FRU."
			INDEX { b8DiskIndex }
			::= { blade8DiskTable 1 }
		
		Blade8DiskEntry ::=
			SEQUENCE { 
				b8DiskIndex
					INTEGER,
				b8DiskMark
					DisplayString,
				b8DiskInfo
					DisplayString,
				b8DiskPresent
					INTEGER,
				b8DiskHealth
					INTEGER,
				b8DiskLocation
					DisplayString
			 }

		b8DiskIndex OBJECT-TYPE
			SYNTAX INTEGER
			MAX-ACCESS not-accessible
			STATUS current
			DESCRIPTION
				"DISK INDEX"
			::= { blade8DiskEntry 1 }
		
		b8DiskMark OBJECT-TYPE
			SYNTAX DisplayString
			MAX-ACCESS read-only
			STATUS current
			DESCRIPTION
				"Get the disk silk-screen."
			::= { blade8DiskEntry 2 }
		
		b8DiskInfo OBJECT-TYPE
			SYNTAX DisplayString
			MAX-ACCESS read-only
			STATUS current
			DESCRIPTION
				"Get the disk description of vendor, capacity and speed."
			::= { blade8DiskEntry 3 }
		
		b8DiskPresent OBJECT-TYPE
			SYNTAX INTEGER
			MAX-ACCESS read-only
			STATUS current
			DESCRIPTION
				"Get the disk presence status."
			::= { blade8DiskEntry 4 }
		
		b8DiskHealth OBJECT-TYPE
			SYNTAX INTEGER
			MAX-ACCESS read-only
			STATUS current
			DESCRIPTION
				"Get the disk health status."
			::= { blade8DiskEntry 5 }
		
		b8DiskLocation OBJECT-TYPE
			SYNTAX DisplayString
			MAX-ACCESS read-only
			STATUS current
			DESCRIPTION
				"Get the disk location."
			::= { blade8DiskEntry 6 }
		
		blade8SecretKvmVmmTable OBJECT-TYPE
			SYNTAX SEQUENCE OF Blade8SecretKvmVmmEntry
			MAX-ACCESS not-accessible
			STATUS current
			DESCRIPTION
				"A table containing the list of Blade8 KVM&VMM secret information."
			::= { blade8 2010 }

		blade8SecretKvmVmmEntry OBJECT-TYPE
			SYNTAX Blade8SecretKvmVmmEntry
			MAX-ACCESS not-accessible
			STATUS current
			DESCRIPTION
				"Information about a particular current KVM&VMM."
			INDEX { b8SecretKvmVmmIndex }
			::= { blade8SecretKvmVmmTable 1 }
		Blade8SecretKvmVmmEntry ::=
			SEQUENCE { 
				b8SecretKvmVmmIndex
					INTEGER,
				b8SecretKvmState
					INTEGER,
				b8SecretVmmState
					INTEGER,
				b8MMSecretVmmKey
					DisplayString,
				b8SecretVmmKey
					DisplayString
			 }
		b8SecretKvmVmmIndex OBJECT-TYPE
			SYNTAX INTEGER
			MAX-ACCESS not-accessible
			STATUS current
			DESCRIPTION
				"KVM&VMM INDEX."
			::= { blade8SecretKvmVmmEntry 1 }
		b8SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade8SecretKvmVmmEntry 2 }
		b8SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade8SecretKvmVmmEntry 3 }
		b8MMSecretVmmKey OBJECT-TYPE
			SYNTAX DisplayString
			MAX-ACCESS read-only
			STATUS current
			DESCRIPTION
				"Get the MM secret VMM key."
			::= { blade8SecretKvmVmmEntry 4 }
		b8SecretVmmKey OBJECT-TYPE
			SYNTAX DisplayString
			MAX-ACCESS read-write
			STATUS current
			DESCRIPTION
				"Set the secret VMM key."
			::= { blade8SecretKvmVmmEntry 5 }
		blade9 OBJECT IDENTIFIER ::= { blades 9 }

		
 		b9DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade9 4 }
		
 		b9PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade9 5 }
		
 		b9Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade9 6 }

		
 		b9Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b9Health information about a particular b9Location. 
				This will be one of the following:
				(0-ok, 1-minor, 2-major, 3-majorandminor,4-critical,5-criticalandminor,6-criticalandmajor,7-criticalandmajorandminor)"
			::= { blade9 8 }
		
 		b9HealthEvents OBJECT-TYPE
			SYNTAX DisplayString
			MAX-ACCESS read-only
			STATUS current
			DESCRIPTION
				"Events that contribute to the b9Health of the b9Location.  
				This is a list of events currently happening on the 
				b9Location."
			::= { blade9 9 }
		
 		b9ClearSEL OBJECT-TYPE
			SYNTAX INTEGER { clear(1) }
			MAX-ACCESS read-write
			STATUS current
			DESCRIPTION
				"Clean the BMC's SEL on the board."
			::= { blade9 12 }
		
 		b9ExDiskBoardPresence OBJECT-TYPE
			SYNTAX INTEGER
				{
				not-present(0),
				present(1)
				}
			MAX-ACCESS read-only
			STATUS current
			DESCRIPTION
				"Used to find out if the extended disk board is present.
				0 - not present
				1 - present"
			::= { blade9 14 }
		
 		b9BladeVersion OBJECT-TYPE
			SYNTAX DisplayString
			MAX-ACCESS read-only
			STATUS current
			DESCRIPTION
				"display the Version of board9."
			::= { blade9 20 }
		
 		b9MACAddress OBJECT-TYPE
			SYNTAX DisplayString
			MAX-ACCESS read-only
			STATUS current
			DESCRIPTION
				"display the MACAddress of board9."
			::= { blade9 21 }
		
				
							
		
 		b9Safepwofftime OBJECT-TYPE
			SYNTAX INTEGER
			MAX-ACCESS read-write
			STATUS current
			DESCRIPTION
				"the safe poweroff time.
				"
			::= { blade9 26 }
		
 		b9BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2] 
				6=Force boot into BIOS Setup
				15=Force boot from Floppy/primary removable media           
				
				"
			::= { blade9 32 }
		
 		b9Systeminfo OBJECT-TYPE
			SYNTAX DisplayString
			MAX-ACCESS read-write
			STATUS current
			DESCRIPTION
				"display the system information of board9."
			::= { blade9 36 }

		
 		b9SystemProperties OBJECT-TYPE
			SYNTAX DisplayString
			MAX-ACCESS read-only
			STATUS current
			DESCRIPTION
				"Get the power of blade1."
			::= { blade9 39 }
		
 		b9BiosCfg OBJECT-TYPE
			SYNTAX DisplayString
			MAX-ACCESS read-write
			STATUS current
			DESCRIPTION
				"Get the power of blade1."
			::= { blade9 40 }
		
 		b9WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade9 41 }
		
 		b9RealTimePower OBJECT-TYPE
			SYNTAX INTEGER
			MAX-ACCESS read-only
			STATUS current
			DESCRIPTION
				" "
			::= { blade9 43 }
		
 		b9PowerCapping OBJECT-TYPE
			SYNTAX DisplayString
			MAX-ACCESS read-write
			STATUS current
			DESCRIPTION
				" "
			::= { blade9 44 }
		
 		b9Powerreference OBJECT-TYPE
			SYNTAX INTEGER
			MAX-ACCESS read-only
			STATUS current
			DESCRIPTION
				" "
			::= { blade9 45 }
		
 		b9ClearBiosConfig OBJECT-TYPE
			SYNTAX INTEGER
			MAX-ACCESS read-write
			STATUS current
			DESCRIPTION
				" "
			::= { blade9 46 }
		
 		b9BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade9 47 }
		
 		b9BmcUserAdd OBJECT-TYPE
			SYNTAX DisplayString
			MAX-ACCESS read-write
			STATUS current
			DESCRIPTION
				"Used to Add the BMC User
				settable format:
				username,passwd"
			::= { blade9 48 }
		
 		b9BmcUserDel OBJECT-TYPE
			SYNTAX DisplayString
			MAX-ACCESS read-write
			STATUS current
			DESCRIPTION
				"Used to Del the BMC User
				settable format:
				username"
			::= { blade9 49 }
		
 		b9BmcUserPasswd OBJECT-TYPE
			SYNTAX DisplayString
			MAX-ACCESS read-write
			STATUS current
			DESCRIPTION
				"Used to Change the BMC User Passwd
				settable format:
				username,passwd"
			::= { blade9 50 }
		
 		b9BmcUserpropertychg OBJECT-TYPE
			SYNTAX DisplayString
			MAX-ACCESS read-write
			STATUS current
			DESCRIPTION
				"Used to Change the BMC User Property
				settable format:
				username,property"
			::= { blade9 51 }
		
 		b9BmcGateway OBJECT-TYPE
			SYNTAX DisplayString
			MAX-ACCESS read-write
			STATUS current
			DESCRIPTION
				"Read or set the gateway."
			::= { blade9 52 }
		
 		b9SlotBitmap OBJECT-TYPE
			SYNTAX INTEGER
			MAX-ACCESS read-only
			STATUS current
			DESCRIPTION
				" "
			::= { blade9 55 }
		
		b9systemGuid OBJECT-TYPE
			SYNTAX DisplayString
			MAX-ACCESS read-only
			STATUS current
			DESCRIPTION
				" "
			::= { blade9 56 }
		
		b9ProductName OBJECT-TYPE
			SYNTAX DisplayString
			MAX-ACCESS read-only
			STATUS current
			DESCRIPTION
				"display the Version of board9."
			::= { blade9 57 }

		b9BundleVersion OBJECT-TYPE
			SYNTAX DisplayString
			MAX-ACCESS read-write
			STATUS current
			DESCRIPTION
				"Get or set the board9 bundle version."
			::= { blade9 58 }

 		blade9SensorTargetTable OBJECT-TYPE
			SYNTAX SEQUENCE OF Blade9SensorTargetEntry
			MAX-ACCESS not-accessible
			STATUS current
			DESCRIPTION
				"A table containing the list of sensor information."
			::= { blade9 2001 }
		
 		blade9SensorTargetEntry OBJECT-TYPE
			SYNTAX Blade9SensorTargetEntry
			MAX-ACCESS not-accessible
			STATUS current
			DESCRIPTION
				"Information about a particular current sensor."
			INDEX { b9Target }
			::= { blade9SensorTargetTable 1 }
		
		Blade9SensorTargetEntry ::=
			SEQUENCE { 
				b9Target
					DisplayString,
				b9Current
					DisplayString,
				b9ThresholdsAll
					DisplayString,
				b9UpperCritical
					DisplayString,
				b9UpperNonCritical
					DisplayString,
				b9UpperNonRecoverable
					DisplayString,
				b9LowerNonCritical
					DisplayString,
				b9LowerCritical
					DisplayString,
				b9LowerNonRecoverable
					DisplayString,
				b9SensorHealth
					INTEGER,
				b9SensorHealthEvents
					DisplayString,
				b9NegativeHysteresis
					DisplayString,
				b9PositiveHysteresis
					DisplayString,
				b9SensorType
					DisplayString,
				b9SensorFRUInfo
					DisplayString
			 }

 		b9Target OBJECT-TYPE
			SYNTAX DisplayString
			MAX-ACCESS not-accessible
			STATUS current
			DESCRIPTION
				"sensor Name"
			::= { blade9SensorTargetEntry 1 }
		
 		b9Current OBJECT-TYPE
			SYNTAX DisplayString
			MAX-ACCESS read-only
			STATUS current
			DESCRIPTION
				"Display the current value of a sensor."
			::= { blade9SensorTargetEntry 2 }
		
 		b9ThresholdsAll OBJECT-TYPE
			SYNTAX DisplayString
			MAX-ACCESS read-only
			STATUS current
			DESCRIPTION
				"All thresholds of a sensor"
			::= { blade9SensorTargetEntry 3 }
		
 		b9UpperCritical OBJECT-TYPE
			SYNTAX DisplayString
			MAX-ACCESS read-write
			STATUS current
			DESCRIPTION
				"Upper critical thresholds"
			::= { blade9SensorTargetEntry 4 }
		
 		b9UpperNonCritical OBJECT-TYPE
			SYNTAX DisplayString
			MAX-ACCESS read-write
			STATUS current
			DESCRIPTION
				"Upper non-critical thresholds"
			::= { blade9SensorTargetEntry 5 }
		
 		b9UpperNonRecoverable OBJECT-TYPE
			SYNTAX DisplayString
			MAX-ACCESS read-write
			STATUS current
			DESCRIPTION
				"Upper non-recoverable thresholds"
			::= { blade9SensorTargetEntry 6 }
		
 		b9LowerNonCritical OBJECT-TYPE
			SYNTAX DisplayString
			MAX-ACCESS read-write
			STATUS current
			DESCRIPTION
				"Lower non-critical thresholds"
			::= { blade9SensorTargetEntry 7 }
		
 		b9LowerCritical OBJECT-TYPE
			SYNTAX DisplayString
			MAX-ACCESS read-write
			STATUS current
			DESCRIPTION
				"Lower critical thresholds"
			::= { blade9SensorTargetEntry 8 }
		
 		b9LowerNonRecoverable OBJECT-TYPE
			SYNTAX DisplayString
			MAX-ACCESS read-write
			STATUS current
			DESCRIPTION
				"Lower non-recoverable thresholds"
			::= { blade9SensorTargetEntry 9 }
		
 		b9SensorHealth OBJECT-TYPE
			SYNTAX INTEGER
				{
				ok(0),
				minor(1),
				major(2),
				critical(3)
				}
			MAX-ACCESS read-only
			STATUS current
			DESCRIPTION
				"b9Health information about a particular b9Location. 
				This will be one of the following:
				(0-ok, 1-minor, 2-major, 3-critical)"
			::= { blade9SensorTargetEntry 10 }
		
 		b9SensorHealthEvents OBJECT-TYPE
			SYNTAX DisplayString
			MAX-ACCESS read-only
			STATUS current
			DESCRIPTION
				"Events that contribute to the b9Health of the b9Location.  
				This is a list of events currently happening on the 
				b9Location."
			::= { blade9SensorTargetEntry 11 }
		
		
 		b9NegativeHysteresis OBJECT-TYPE
			SYNTAX DisplayString
			MAX-ACCESS read-write
			STATUS current
			DESCRIPTION
				"Get/Set the negativeHysteresis value"
			::= { blade9SensorTargetEntry 16 }
		
 		b9PositiveHysteresis OBJECT-TYPE
			SYNTAX DisplayString
			MAX-ACCESS read-write
			STATUS current
			DESCRIPTION
				"Get/Set the positiveHysteresis value."
			::= { blade9SensorTargetEntry 17 }
		
 		b9SensorType OBJECT-TYPE
			SYNTAX DisplayString
			MAX-ACCESS read-only
			STATUS current
			DESCRIPTION
				"Get the type of the sensor."
			::= { blade9SensorTargetEntry 18 }
		
 		b9SensorFRUInfo OBJECT-TYPE
			SYNTAX DisplayString
			MAX-ACCESS read-only
			STATUS current
			DESCRIPTION
				"Get the fruinfo of the sensor."
			::= { blade9SensorTargetEntry 19 }
		
 		blade9FruTable OBJECT-TYPE
			SYNTAX SEQUENCE OF Blade9FruEntry
			MAX-ACCESS not-accessible
			STATUS current
			DESCRIPTION
				"A table containing the list of FRU information."
			::= { blade9 2002 }
		
 		blade9FruEntry OBJECT-TYPE
			SYNTAX Blade9FruEntry
			MAX-ACCESS not-accessible
			STATUS current
			DESCRIPTION
				"Information about a particular current FRU."
			INDEX { b9fruNumber }
			::= { blade9FruTable 1 }
		
		Blade9FruEntry ::=
			SEQUENCE { 
				b9fruNumber
					INTEGER,
				b9FruHotSwapState
					DisplayString,
				b9FruLedProperties
					DisplayString,
				b9FRUControl
					INTEGER,
				b9FRULabel
					DisplayString,
				b9ResetReason
					DisplayString
			 }

 		b9fruNumber OBJECT-TYPE
			SYNTAX INTEGER
			MAX-ACCESS not-accessible
			STATUS current
			DESCRIPTION
				" "
			::= { blade9FruEntry 1 }
		
 		b9FruHotSwapState OBJECT-TYPE
			SYNTAX DisplayString
			MAX-ACCESS read-only
			STATUS current
			DESCRIPTION
				"Retrieve the hot swap state of the FRU from the 
				internally known hot swap states of blade9."
			::= { blade9FruEntry 3 }
		
 		b9FruLedProperties OBJECT-TYPE
			SYNTAX DisplayString
			MAX-ACCESS read-only
			STATUS current
			DESCRIPTION
				"Retrieves the LED support information from a FRU. Returns a comma separated
				list of LEDS and the number of FRU supported user LEDs."
			::= { blade9FruEntry 4 }

		

		b9FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade9FruEntry 9 }
		
 		b9FRULabel OBJECT-TYPE
			SYNTAX DisplayString
			MAX-ACCESS read-only
			STATUS current
			DESCRIPTION
				"Get fru label of blade9."
			::= { blade9FruEntry 10 }
		
 		b9ResetReason OBJECT-TYPE
			SYNTAX DisplayString
			MAX-ACCESS read-only
			STATUS current
			DESCRIPTION
				"Delete fru label of smm."
			::= { blade9FruEntry 11 }
		
 		blade9FruLedTable OBJECT-TYPE
			SYNTAX SEQUENCE OF Blade9FruLedEntry
			MAX-ACCESS not-accessible
			STATUS current
			DESCRIPTION
				"A table containing the list of led information."
			::= { blade9 2003 }
		
 		blade9FruLedEntry OBJECT-TYPE
			SYNTAX Blade9FruLedEntry
			MAX-ACCESS not-accessible
			STATUS current
			DESCRIPTION
				"Information about a particular current led."
			INDEX { b9FruID, b9FruLed }
			::= { blade9FruLedTable 1 }
		
		Blade9FruLedEntry ::=
			SEQUENCE { 
				b9FruID
					INTEGER,
				b9FruLed
					DisplayString,
				b9FruLedColorProps
					DisplayString,
				b9FruLedState
					DisplayString
			 }

 		b9FruID OBJECT-TYPE
			SYNTAX INTEGER
			MAX-ACCESS not-accessible
			STATUS current
			DESCRIPTION
				" "
			::= { blade9FruLedEntry 1 }
		
 		b9FruLed OBJECT-TYPE
			SYNTAX DisplayString
			MAX-ACCESS not-accessible
			STATUS current
			DESCRIPTION
				" "
			::= { blade9FruLedEntry 2 }
		
 		b9FruLedColorProps OBJECT-TYPE
			SYNTAX DisplayString
			MAX-ACCESS read-only
			STATUS current
			DESCRIPTION
				"Finds out what colors are supported by the LED"
			::= { blade9FruLedEntry 3 }
		
 		b9FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade9FruLedEntry 4 }
		
 		blade9FruDescriptionTable OBJECT-TYPE
			SYNTAX SEQUENCE OF Blade9FruDescriptionEntry
			MAX-ACCESS not-accessible
			STATUS current
			DESCRIPTION
				"A table containing the list of blade9 FRU information."
			::= { blade9 2004 }
		
 		blade9FruDescriptionEntry OBJECT-TYPE
			SYNTAX Blade9FruDescriptionEntry
			MAX-ACCESS not-accessible
			STATUS current
			DESCRIPTION
				"Information about a particular current FRU."
			INDEX { b9fruNum }
			::= { blade9FruDescriptionTable 1 }
		
		Blade9FruDescriptionEntry ::=
			SEQUENCE { 
				b9fruNum
					INTEGER,
				b9fruBoardDescription
					DisplayString,
				b9fruBoardManufacturer
					DisplayString,
				b9fruBoardPartNumber
					DisplayString,
				b9fruBoardSerialNumber
					DisplayString,
				b9fruBoardManufactureDate
					DisplayString,
				b9fruProductDescription
					DisplayString,
				b9fruProductManufacturer
					DisplayString,
				b9fruProductPartNumber
					DisplayString,
				b9fruProductSerialNumber
					DisplayString,
				b9fruProductRevision
					DisplayString,
				b9fruAll
					DisplayString
			 }

 		b9fruNum OBJECT-TYPE
			SYNTAX INTEGER
			MAX-ACCESS not-accessible
			STATUS current
			DESCRIPTION
				"blade9 FRU's INDEX"
			::= { blade9FruDescriptionEntry 1 }
		
 		b9fruBoardDescription OBJECT-TYPE
			SYNTAX DisplayString
			MAX-ACCESS read-only
			STATUS current
			DESCRIPTION
				"Used to read the Board Description from the blade9 fru."
			::= { blade9FruDescriptionEntry 2 }
		
 		b9fruBoardManufacturer OBJECT-TYPE
			SYNTAX DisplayString
			MAX-ACCESS read-only
			STATUS current
			DESCRIPTION
				"Used to read the Board Manufacturer from the bladef9 fru."
			::= { blade9FruDescriptionEntry 3 }
		
 		b9fruBoardPartNumber OBJECT-TYPE
			SYNTAX DisplayString
			MAX-ACCESS read-only
			STATUS current
			DESCRIPTION
				"Used to read the Board Part Number from the blade9 fru."
			::= { blade9FruDescriptionEntry 4 }
		
 		b9fruBoardSerialNumber OBJECT-TYPE
			SYNTAX DisplayString
			MAX-ACCESS read-only
			STATUS current
			DESCRIPTION
				"Used to read the Board Serial Number from the blade9 fru."
			::= { blade9FruDescriptionEntry 5 }
		
 		b9fruBoardManufactureDate OBJECT-TYPE
			SYNTAX DisplayString
			MAX-ACCESS read-only
			STATUS current
			DESCRIPTION
				"Used to read the Board Manufacture Date from the blade9 fru."
			::= { blade9FruDescriptionEntry 6 }
		
 		b9fruProductDescription OBJECT-TYPE
			SYNTAX DisplayString
			MAX-ACCESS read-only
			STATUS current
			DESCRIPTION
				"Used to read the Product Description from the blade9 fru."
			::= { blade9FruDescriptionEntry 7 }
		
 		b9fruProductManufacturer OBJECT-TYPE
			SYNTAX DisplayString
			MAX-ACCESS read-only
			STATUS current
			DESCRIPTION
				"Used to read the Product Manufacturer from the blade9 fru."
			::= { blade9FruDescriptionEntry 8 }
		
 		b9fruProductPartNumber OBJECT-TYPE
			SYNTAX DisplayString
			MAX-ACCESS read-only
			STATUS current
			DESCRIPTION
				"Used to read the Product Part Number from the blade9 fru."
			::= { blade9FruDescriptionEntry 9 }
		
 		b9fruProductSerialNumber OBJECT-TYPE
			SYNTAX DisplayString
			MAX-ACCESS read-only
			STATUS current
			DESCRIPTION
				"Used to read the Product Serial Number from the blade9 fru."
			::= { blade9FruDescriptionEntry 10 }
		
 		b9fruProductRevision OBJECT-TYPE
			SYNTAX DisplayString
			MAX-ACCESS read-only
			STATUS current
			DESCRIPTION
				"Used to read the Product Revision from the blade9 fru."
			::= { blade9FruDescriptionEntry 13 }
		
 		b9fruAll OBJECT-TYPE
			SYNTAX DisplayString
			MAX-ACCESS read-only
			STATUS current
			DESCRIPTION
				"Used to read the fru info all."
			::= { blade9FruDescriptionEntry 14 }
		
		blade9CPUTable OBJECT-TYPE
			SYNTAX SEQUENCE OF Blade9CPUEntry
			MAX-ACCESS not-accessible
			STATUS current
			DESCRIPTION
				"A table containing the list of Blade1 FRU information."
			::= { blade9 2006 }
		
		blade9CPUEntry OBJECT-TYPE
			SYNTAX Blade9CPUEntry
			MAX-ACCESS not-accessible
			STATUS current
			DESCRIPTION
				"Information about a particular current FRU."
			INDEX { b9CPUIndex }
			::= { blade9CPUTable 1 }
		
		Blade9CPUEntry ::=
			SEQUENCE { 
				b9CPUIndex
					INTEGER,
				b9CPUMark
					DisplayString,
				b9CPUInfo
					DisplayString,
				b9CPUPresent
					INTEGER,
				b9CPUHealth
					INTEGER,
				b9CPULocation
					DisplayString
			 }

		b9CPUIndex OBJECT-TYPE
			SYNTAX INTEGER
			MAX-ACCESS not-accessible
			STATUS current
			DESCRIPTION
				"CPU INDEX"
			::= { blade9CPUEntry 1 }
		
		b9CPUMark OBJECT-TYPE
			SYNTAX DisplayString
			MAX-ACCESS read-only
			STATUS current
			DESCRIPTION
				"Get the CPU silk-screen."
			::= { blade9CPUEntry 2 }
		
		b9CPUInfo OBJECT-TYPE
			SYNTAX DisplayString
			MAX-ACCESS read-only
			STATUS current
			DESCRIPTION
				"Get the CPU description of vendor, type and frequency."
			::= { blade9CPUEntry 3 }
		
		b9CPUPresent OBJECT-TYPE
			SYNTAX INTEGER
			MAX-ACCESS read-only
			STATUS current
			DESCRIPTION
				"Get the CPU presence status."
			::= { blade9CPUEntry 4 }
		
		b9CPUHealth OBJECT-TYPE
			SYNTAX INTEGER
			MAX-ACCESS read-only
			STATUS current
			DESCRIPTION
				"Get the CPU health status."
			::= { blade9CPUEntry 5 }
		
		b9CPULocation OBJECT-TYPE
			SYNTAX DisplayString
			MAX-ACCESS read-only
			STATUS current
			DESCRIPTION
				"Get the CPU location."
			::= { blade9CPUEntry 6 }
		
		blade9MemoryTable OBJECT-TYPE
			SYNTAX SEQUENCE OF Blade9MemoryEntry
			MAX-ACCESS not-accessible
			STATUS current
			DESCRIPTION
				"A table containing the list of Blade1 FRU information."
			::= { blade9 2007 }
		
		blade9MemoryEntry OBJECT-TYPE
			SYNTAX Blade9MemoryEntry
			MAX-ACCESS not-accessible
			STATUS current
			DESCRIPTION
				"Information about a particular current FRU."
			INDEX { b9MEMIndex }
			::= { blade9MemoryTable 1 }
		
		Blade9MemoryEntry ::=
			SEQUENCE { 
				b9MEMIndex
					INTEGER,
				b9MEMMark
					DisplayString,
				b9MEMInfo
					DisplayString,
				b9MEMPresent
					INTEGER,
				b9MEMHealth
					INTEGER,
				b9MEMLocation
					DisplayString
			 }

		b9MEMIndex OBJECT-TYPE
			SYNTAX INTEGER
			MAX-ACCESS not-accessible
			STATUS current
			DESCRIPTION
				"MEMORY INDEX"
			::= { blade9MemoryEntry 1 }
		
		b9MEMMark OBJECT-TYPE
			SYNTAX DisplayString
			MAX-ACCESS read-only
			STATUS current
			DESCRIPTION
				"Get the memory silk-screen."
			::= { blade9MemoryEntry 2 }
		
		b9MEMInfo OBJECT-TYPE
			SYNTAX DisplayString
			MAX-ACCESS read-only
			STATUS current
			DESCRIPTION
				"Get the memory description of vendor, frequency and capacity."
			::= { blade9MemoryEntry 3 }
		
		b9MEMPresent OBJECT-TYPE
			SYNTAX INTEGER
			MAX-ACCESS read-only
			STATUS current
			DESCRIPTION
				"Get the memory presence status."
			::= { blade9MemoryEntry 4 }
		
		b9MEMHealth OBJECT-TYPE
			SYNTAX INTEGER
			MAX-ACCESS read-only
			STATUS current
			DESCRIPTION
				"Get the memory health status."
			::= { blade9MemoryEntry 5 }
		
		b9MEMLocation OBJECT-TYPE
			SYNTAX DisplayString
			MAX-ACCESS read-only
			STATUS current
			DESCRIPTION
				"Get the memory location."
			::= { blade9MemoryEntry 6 }
		
		blade9MezzTable OBJECT-TYPE
			SYNTAX SEQUENCE OF Blade9MezzEntry
			MAX-ACCESS not-accessible
			STATUS current
			DESCRIPTION
				"A table containing the list of Blade1 FRU information."
			::= { blade9 2008 }
		
		blade9MezzEntry OBJECT-TYPE
			SYNTAX Blade9MezzEntry
			MAX-ACCESS not-accessible
			STATUS current
			DESCRIPTION
				"Information about a particular current FRU."
			INDEX { b9MezzIndex }
			::= { blade9MezzTable 1 }
		
		Blade9MezzEntry ::=
			SEQUENCE { 
				b9MezzIndex
					INTEGER,
				b9MezzMark
					DisplayString,
				b9MezzInfo
					DisplayString,
				b9MezzPresent
					INTEGER,
				b9MezzHealth
					INTEGER,
				b9MezzLocation
					DisplayString,
				b9MezzMac
					DisplayString
			 }

		b9MezzIndex OBJECT-TYPE
			SYNTAX INTEGER
			MAX-ACCESS not-accessible
			STATUS current
			DESCRIPTION
				"MEZZ INDEX"
			::= { blade9MezzEntry 1 }
		
		b9MezzMark OBJECT-TYPE
			SYNTAX DisplayString
			MAX-ACCESS read-only
			STATUS current
			DESCRIPTION
				"Get the MEZZ silk-screen."
			::= { blade9MezzEntry 2 }
		
		b9MezzInfo OBJECT-TYPE
			SYNTAX DisplayString
			MAX-ACCESS read-only
			STATUS current
			DESCRIPTION
				"Get the MEZZ description of type."
			::= { blade9MezzEntry 3 }
		
		b9MezzPresent OBJECT-TYPE
			SYNTAX INTEGER
			MAX-ACCESS read-only
			STATUS current
			DESCRIPTION
				"Get the MEZZ presence status."
			::= { blade9MezzEntry 4 }
		
		b9MezzHealth OBJECT-TYPE
			SYNTAX INTEGER
			MAX-ACCESS read-only
			STATUS current
			DESCRIPTION
				"Get the MEZZ health status."
			::= { blade9MezzEntry 5 }
		
		b9MezzLocation OBJECT-TYPE
			SYNTAX DisplayString
			MAX-ACCESS read-only
			STATUS current
			DESCRIPTION
				"Get the MEZZ location."
			::= { blade9MezzEntry 6 }
		
		b9MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade9MezzEntry 7 }
		
		blade9DiskTable OBJECT-TYPE
			SYNTAX SEQUENCE OF Blade9DiskEntry
			MAX-ACCESS not-accessible
			STATUS current
			DESCRIPTION
				"A table containing the list of Blade1 FRU information."
			::= { blade9 2009 }
		
		blade9DiskEntry OBJECT-TYPE
			SYNTAX Blade9DiskEntry
			MAX-ACCESS not-accessible
			STATUS current
			DESCRIPTION
				"Information about a particular current FRU."
			INDEX { b9DiskIndex }
			::= { blade9DiskTable 1 }
		
		Blade9DiskEntry ::=
			SEQUENCE { 
				b9DiskIndex
					INTEGER,
				b9DiskMark
					DisplayString,
				b9DiskInfo
					DisplayString,
				b9DiskPresent
					INTEGER,
				b9DiskHealth
					INTEGER,
				b9DiskLocation
					DisplayString
			 }

		b9DiskIndex OBJECT-TYPE
			SYNTAX INTEGER
			MAX-ACCESS not-accessible
			STATUS current
			DESCRIPTION
				"DISK INDEX"
			::= { blade9DiskEntry 1 }
		
		b9DiskMark OBJECT-TYPE
			SYNTAX DisplayString
			MAX-ACCESS read-only
			STATUS current
			DESCRIPTION
				"Get the disk silk-screen."
			::= { blade9DiskEntry 2 }
		
		b9DiskInfo OBJECT-TYPE
			SYNTAX DisplayString
			MAX-ACCESS read-only
			STATUS current
			DESCRIPTION
				"Get the disk description of vendor, capacity and speed."
			::= { blade9DiskEntry 3 }
		
		b9DiskPresent OBJECT-TYPE
			SYNTAX INTEGER
			MAX-ACCESS read-only
			STATUS current
			DESCRIPTION
				"Get the disk presence status."
			::= { blade9DiskEntry 4 }
		
		b9DiskHealth OBJECT-TYPE
			SYNTAX INTEGER
			MAX-ACCESS read-only
			STATUS current
			DESCRIPTION
				"Get the disk health status."
			::= { blade9DiskEntry 5 }
		
		b9DiskLocation OBJECT-TYPE
			SYNTAX DisplayString
			MAX-ACCESS read-only
			STATUS current
			DESCRIPTION
				"Get the disk location."
			::= { blade9DiskEntry 6 }
		
		blade9SecretKvmVmmTable OBJECT-TYPE
			SYNTAX SEQUENCE OF Blade9SecretKvmVmmEntry
			MAX-ACCESS not-accessible
			STATUS current
			DESCRIPTION
				"A table containing the list of Blade9 KVM&VMM secret information."
			::= { blade9 2010 }

		blade9SecretKvmVmmEntry OBJECT-TYPE
			SYNTAX Blade9SecretKvmVmmEntry
			MAX-ACCESS not-accessible
			STATUS current
			DESCRIPTION
				"Information about a particular current KVM&VMM."
			INDEX { b9SecretKvmVmmIndex }
			::= { blade9SecretKvmVmmTable 1 }
		Blade9SecretKvmVmmEntry ::=
			SEQUENCE { 
				b9SecretKvmVmmIndex
					INTEGER,
				b9SecretKvmState
					INTEGER,
				b9SecretVmmState
					INTEGER,
				b9MMSecretVmmKey
					DisplayString,
				b9SecretVmmKey
					DisplayString
			 }
		b9SecretKvmVmmIndex OBJECT-TYPE
			SYNTAX INTEGER
			MAX-ACCESS not-accessible
			STATUS current
			DESCRIPTION
				"KVM&VMM INDEX."
			::= { blade9SecretKvmVmmEntry 1 }
		b9SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade9SecretKvmVmmEntry 2 }
		b9SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade9SecretKvmVmmEntry 3 }
		b9MMSecretVmmKey OBJECT-TYPE
			SYNTAX DisplayString
			MAX-ACCESS read-only
			STATUS current
			DESCRIPTION
				"Get the MM secret VMM key."
			::= { blade9SecretKvmVmmEntry 4 }
		b9SecretVmmKey OBJECT-TYPE
			SYNTAX DisplayString
			MAX-ACCESS read-write
			STATUS current
			DESCRIPTION
				"Set the secret VMM key."
			::= { blade9SecretKvmVmmEntry 5 }
		blade10 OBJECT IDENTIFIER ::= { blades 10 }

		
 		b10DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade10 4 }
		
 		b10PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade10 5 }
		
 		b10Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade10 6 }

		
 		b10Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b10Health information about a particular b10Location. 
				This will be one of the following:
				(0-ok, 1-minor, 2-major, 3-majorandminor,4-critical,5-criticalandminor,6-criticalandmajor,7-criticalandmajorandminor)"
			::= { blade10 8 }
		
 		b10HealthEvents OBJECT-TYPE
			SYNTAX DisplayString
			MAX-ACCESS read-only
			STATUS current
			DESCRIPTION
				"Events that contribute to the b10Health of the b10Location.  
				This is a list of events currently happening on the 
				b10Location."
			::= { blade10 9 }
		
 		b10ClearSEL OBJECT-TYPE
			SYNTAX INTEGER { clear(1) }
			MAX-ACCESS read-write
			STATUS current
			DESCRIPTION
				"Clean the BMC's SEL on the board."
			::= { blade10 12 }
		
 		b10ExDiskBoardPresence OBJECT-TYPE
			SYNTAX INTEGER
				{
				not-present(0),
				present(1)
				}
			MAX-ACCESS read-only
			STATUS current
			DESCRIPTION
				"Used to find out if the extended disk board is present.
				0 - not present
				1 - present"
			::= { blade10 14 }
		
 		b10BladeVersion OBJECT-TYPE
			SYNTAX DisplayString
			MAX-ACCESS read-only
			STATUS current
			DESCRIPTION
				"display the Version of board10."
			::= { blade10 20 }
		
 		b10MACAddress OBJECT-TYPE
			SYNTAX DisplayString
			MAX-ACCESS read-only
			STATUS current
			DESCRIPTION
				"display the MACAddress of board10."
			::= { blade10 21 }
		
				
							
		
 		b10Safepwofftime OBJECT-TYPE
			SYNTAX INTEGER
			MAX-ACCESS read-write
			STATUS current
			DESCRIPTION
				"the safe poweroff time.
				"
			::= { blade10 26 }
		
 		b10BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade10 32 }
		
 		b10Systeminfo OBJECT-TYPE
			SYNTAX DisplayString
			MAX-ACCESS read-write
			STATUS current
			DESCRIPTION
				"display the system information of board10."
			::= { blade10 36 }

		
 		b10SystemProperties OBJECT-TYPE
			SYNTAX DisplayString
			MAX-ACCESS read-only
			STATUS current
			DESCRIPTION
				"Get the power of blade1."
			::= { blade10 39 }
		
 		b10BiosCfg OBJECT-TYPE
			SYNTAX DisplayString
			MAX-ACCESS read-write
			STATUS current
			DESCRIPTION
				"Get the power of blade1."
			::= { blade10 40 }
		
 		b10WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade10 41 }
		
 		b10RealTimePower OBJECT-TYPE
			SYNTAX INTEGER
			MAX-ACCESS read-only
			STATUS current
			DESCRIPTION
				" "
			::= { blade10 43 }
		
 		b10PowerCapping OBJECT-TYPE
			SYNTAX DisplayString
			MAX-ACCESS read-write
			STATUS current
			DESCRIPTION
				" "
			::= { blade10 44 }
		
 		b10Powerreference OBJECT-TYPE
			SYNTAX INTEGER
			MAX-ACCESS read-only
			STATUS current
			DESCRIPTION
				" "
			::= { blade10 45 }
		
 		b10ClearBiosConfig OBJECT-TYPE
			SYNTAX INTEGER
			MAX-ACCESS read-write
			STATUS current
			DESCRIPTION
				" "
			::= { blade10 46 }
		
 		b10BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade10 47 }
		
 		b10BmcUserAdd OBJECT-TYPE
			SYNTAX DisplayString
			MAX-ACCESS read-write
			STATUS current
			DESCRIPTION
				"Used to Add the BMC User
				settable format:
				username,passwd"
			::= { blade10 48 }
		
 		b10BmcUserDel OBJECT-TYPE
			SYNTAX DisplayString
			MAX-ACCESS read-write
			STATUS current
			DESCRIPTION
				"Used to Del the BMC User
				settable format:
				username"
			::= { blade10 49 }
		
 		b10BmcUserPasswd OBJECT-TYPE
			SYNTAX DisplayString
			MAX-ACCESS read-write
			STATUS current
			DESCRIPTION
				"Used to Change the BMC User Passwd
				settable format:
				username,passwd"
			::= { blade10 50 }
		
 		b10BmcUserpropertychg OBJECT-TYPE
			SYNTAX DisplayString
			MAX-ACCESS read-write
			STATUS current
			DESCRIPTION
				"Used to Change the BMC User Property
				settable format:
				username,property"
			::= { blade10 51 }
		
 		b10BmcGateway OBJECT-TYPE
			SYNTAX DisplayString
			MAX-ACCESS read-write
			STATUS current
			DESCRIPTION
				"Read or set the gateway."
			::= { blade10 52 }
		
 		b10SlotBitmap OBJECT-TYPE
			SYNTAX INTEGER
			MAX-ACCESS read-only
			STATUS current
			DESCRIPTION
				" "
			::= { blade10 55 }
		
		b10systemGuid OBJECT-TYPE
			SYNTAX DisplayString
			MAX-ACCESS read-only
			STATUS current
			DESCRIPTION
				" "
			::= { blade10 56 }
		
		b10ProductName OBJECT-TYPE
			SYNTAX DisplayString
			MAX-ACCESS read-only
			STATUS current
			DESCRIPTION
				"display the Version of board10."
			::= { blade10 57 }

		b10BundleVersion OBJECT-TYPE
			SYNTAX DisplayString
			MAX-ACCESS read-write
			STATUS current
			DESCRIPTION
				"Get or set the board10 bundle version."
			::= { blade10 58 }

 		blade10SensorTargetTable OBJECT-TYPE
			SYNTAX SEQUENCE OF Blade10SensorTargetEntry
			MAX-ACCESS not-accessible
			STATUS current
			DESCRIPTION
				"A table containing the list of sensor information."
			::= { blade10 2001 }
		
 		blade10SensorTargetEntry OBJECT-TYPE
			SYNTAX Blade10SensorTargetEntry
			MAX-ACCESS not-accessible
			STATUS current
			DESCRIPTION
				"Information about a particular current sensor."
			INDEX { b10Target }
			::= { blade10SensorTargetTable 1 }
		
		Blade10SensorTargetEntry ::=
			SEQUENCE { 
				b10Target
					DisplayString,
				b10Current
					DisplayString,
				b10ThresholdsAll
					DisplayString,
				b10UpperCritical
					DisplayString,
				b10UpperNonCritical
					DisplayString,
				b10UpperNonRecoverable
					DisplayString,
				b10LowerNonCritical
					DisplayString,
				b10LowerCritical
					DisplayString,
				b10LowerNonRecoverable
					DisplayString,
				b10SensorHealth
					INTEGER,
				b10SensorHealthEvents
					DisplayString,
				b10NegativeHysteresis
					DisplayString,
				b10PositiveHysteresis
					DisplayString,
				b10SensorType
					DisplayString,
				b10SensorFRUInfo
					DisplayString
			 }

 		b10Target OBJECT-TYPE
			SYNTAX DisplayString
			MAX-ACCESS not-accessible
			STATUS current
			DESCRIPTION
				"sensor Name"
			::= { blade10SensorTargetEntry 1 }
		
 		b10Current OBJECT-TYPE
			SYNTAX DisplayString
			MAX-ACCESS read-only
			STATUS current
			DESCRIPTION
				"Display the current value of a sensor."
			::= { blade10SensorTargetEntry 2 }
		
 		b10ThresholdsAll OBJECT-TYPE
			SYNTAX DisplayString
			MAX-ACCESS read-only
			STATUS current
			DESCRIPTION
				"All thresholds of a sensor"
			::= { blade10SensorTargetEntry 3 }
		
 		b10UpperCritical OBJECT-TYPE
			SYNTAX DisplayString
			MAX-ACCESS read-write
			STATUS current
			DESCRIPTION
				"Upper critical thresholds"
			::= { blade10SensorTargetEntry 4 }
		
 		b10UpperNonCritical OBJECT-TYPE
			SYNTAX DisplayString
			MAX-ACCESS read-write
			STATUS current
			DESCRIPTION
				"Upper non-critical thresholds"
			::= { blade10SensorTargetEntry 5 }
		
 		b10UpperNonRecoverable OBJECT-TYPE
			SYNTAX DisplayString
			MAX-ACCESS read-write
			STATUS current
			DESCRIPTION
				"Upper non-recoverable thresholds"
			::= { blade10SensorTargetEntry 6 }
		
 		b10LowerNonCritical OBJECT-TYPE
			SYNTAX DisplayString
			MAX-ACCESS read-write
			STATUS current
			DESCRIPTION
				"Lower non-critical thresholds"
			::= { blade10SensorTargetEntry 7 }
		
 		b10LowerCritical OBJECT-TYPE
			SYNTAX DisplayString
			MAX-ACCESS read-write
			STATUS current
			DESCRIPTION
				"Lower critical thresholds"
			::= { blade10SensorTargetEntry 8 }
		
 		b10LowerNonRecoverable OBJECT-TYPE
			SYNTAX DisplayString
			MAX-ACCESS read-write
			STATUS current
			DESCRIPTION
				"Lower non-recoverable thresholds"
			::= { blade10SensorTargetEntry 9 }
		
 		b10SensorHealth OBJECT-TYPE
			SYNTAX INTEGER
				{
				ok(0),
				minor(1),
				major(2),
				critical(3)
				}
			MAX-ACCESS read-only
			STATUS current
			DESCRIPTION
				"b10Health information about a particular b10Location. 
				This will be one of the following:
				(0-ok, 1-minor, 2-major, 3-critical)"
			::= { blade10SensorTargetEntry 10 }
		
 		b10SensorHealthEvents OBJECT-TYPE
			SYNTAX DisplayString
			MAX-ACCESS read-only
			STATUS current
			DESCRIPTION
				"Events that contribute to the b10Health of the b10Location.  
				This is a list of events currently happening on the 
				b10Location."
			::= { blade10SensorTargetEntry 11 }
		
		
 		b10NegativeHysteresis OBJECT-TYPE
			SYNTAX DisplayString
			MAX-ACCESS read-write
			STATUS current
			DESCRIPTION
				"Get/Set the negativeHysteresis value"
			::= { blade10SensorTargetEntry 16 }
		
 		b10PositiveHysteresis OBJECT-TYPE
			SYNTAX DisplayString
			MAX-ACCESS read-write
			STATUS current
			DESCRIPTION
				"Get/Set the positiveHysteresis value."
			::= { blade10SensorTargetEntry 17 }
		
 		b10SensorType OBJECT-TYPE
			SYNTAX DisplayString
			MAX-ACCESS read-only
			STATUS current
			DESCRIPTION
				"Get the type of the sensor."
			::= { blade10SensorTargetEntry 18 }
		
 		b10SensorFRUInfo OBJECT-TYPE
			SYNTAX DisplayString
			MAX-ACCESS read-only
			STATUS current
			DESCRIPTION
				"Get the fruinfo of the sensor."
			::= { blade10SensorTargetEntry 19 }
		
 		blade10FruTable OBJECT-TYPE
			SYNTAX SEQUENCE OF Blade10FruEntry
			MAX-ACCESS not-accessible
			STATUS current
			DESCRIPTION
				"A table containing the list of FRU information."
			::= { blade10 2002 }
		
 		blade10FruEntry OBJECT-TYPE
			SYNTAX Blade10FruEntry
			MAX-ACCESS not-accessible
			STATUS current
			DESCRIPTION
				"Information about a particular current FRU."
			INDEX { b10fruNumber }
			::= { blade10FruTable 1 }
		
		Blade10FruEntry ::=
			SEQUENCE { 
				b10fruNumber
					INTEGER,
				b10FruHotSwapState
					DisplayString,
				b10FruLedProperties
					DisplayString,
				b10FRUControl
					INTEGER,
				b10FRULabel
					DisplayString,
				b10ResetReason
					DisplayString
			 }

 		b10fruNumber OBJECT-TYPE
			SYNTAX INTEGER
			MAX-ACCESS not-accessible
			STATUS current
			DESCRIPTION
				" "
			::= { blade10FruEntry 1 }
		
 		b10FruHotSwapState OBJECT-TYPE
			SYNTAX DisplayString
			MAX-ACCESS read-only
			STATUS current
			DESCRIPTION
				"Retrieve the hot swap state of the FRU from the 
				internally known hot swap states of blade10."
			::= { blade10FruEntry 3 }
		
 		b10FruLedProperties OBJECT-TYPE
			SYNTAX DisplayString
			MAX-ACCESS read-only
			STATUS current
			DESCRIPTION
				"Retrieves the LED support information from a FRU. Returns a comma separated
				list of LEDS and the number of FRU supported user LEDs."
			::= { blade10FruEntry 4 }

		

		b10FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade10FruEntry 9 }
		
 		b10FRULabel OBJECT-TYPE
			SYNTAX DisplayString
			MAX-ACCESS read-only
			STATUS current
			DESCRIPTION
				"Get fru label of blade10."
			::= { blade10FruEntry 10 }
		
 		b10ResetReason OBJECT-TYPE
			SYNTAX DisplayString
			MAX-ACCESS read-only
			STATUS current
			DESCRIPTION
				"Delete fru label of smm."
			::= { blade10FruEntry 11 }
		
 		blade10FruLedTable OBJECT-TYPE
			SYNTAX SEQUENCE OF Blade10FruLedEntry
			MAX-ACCESS not-accessible
			STATUS current
			DESCRIPTION
				"A table containing the list of led information."
			::= { blade10 2003 }
		
 		blade10FruLedEntry OBJECT-TYPE
			SYNTAX Blade10FruLedEntry
			MAX-ACCESS not-accessible
			STATUS current
			DESCRIPTION
				"Information about a particular current led."
			INDEX { b10FruID, b10FruLed }
			::= { blade10FruLedTable 1 }
		
		Blade10FruLedEntry ::=
			SEQUENCE { 
				b10FruID
					INTEGER,
				b10FruLed
					DisplayString,
				b10FruLedColorProps
					DisplayString,
				b10FruLedState
					DisplayString
			 }

 		b10FruID OBJECT-TYPE
			SYNTAX INTEGER
			MAX-ACCESS not-accessible
			STATUS current
			DESCRIPTION
				" "
			::= { blade10FruLedEntry 1 }
		
 		b10FruLed OBJECT-TYPE
			SYNTAX DisplayString
			MAX-ACCESS not-accessible
			STATUS current
			DESCRIPTION
				" "
			::= { blade10FruLedEntry 2 }
		
 		b10FruLedColorProps OBJECT-TYPE
			SYNTAX DisplayString
			MAX-ACCESS read-only
			STATUS current
			DESCRIPTION
				"Finds out what colors are supported by the LED"
			::= { blade10FruLedEntry 3 }
		
 		b10FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade10FruLedEntry 4 }
		
 		blade10FruDescriptionTable OBJECT-TYPE
			SYNTAX SEQUENCE OF Blade10FruDescriptionEntry
			MAX-ACCESS not-accessible
			STATUS current
			DESCRIPTION
				"A table containing the list of blade10 FRU information."
			::= { blade10 2004 }
		
 		blade10FruDescriptionEntry OBJECT-TYPE
			SYNTAX Blade10FruDescriptionEntry
			MAX-ACCESS not-accessible
			STATUS current
			DESCRIPTION
				"Information about a particular current FRU."
			INDEX { b10fruNum }
			::= { blade10FruDescriptionTable 1 }
		
		Blade10FruDescriptionEntry ::=
			SEQUENCE { 
				b10fruNum
					INTEGER,
				b10fruBoardDescription
					DisplayString,
				b10fruBoardManufacturer
					DisplayString,
				b10fruBoardPartNumber
					DisplayString,
				b10fruBoardSerialNumber
					DisplayString,
				b10fruBoardManufactureDate
					DisplayString,
				b10fruProductDescription
					DisplayString,
				b10fruProductManufacturer
					DisplayString,
				b10fruProductPartNumber
					DisplayString,
				b10fruProductSerialNumber
					DisplayString,
				b10fruProductRevision
					DisplayString,
				b10fruAll
					DisplayString
			 }

 		b10fruNum OBJECT-TYPE
			SYNTAX INTEGER
			MAX-ACCESS not-accessible
			STATUS current
			DESCRIPTION
				"blade10 FRU's INDEX"
			::= { blade10FruDescriptionEntry 1 }
		
 		b10fruBoardDescription OBJECT-TYPE
			SYNTAX DisplayString
			MAX-ACCESS read-only
			STATUS current
			DESCRIPTION
				"Used to read the Board Description from the blade10 fru."
			::= { blade10FruDescriptionEntry 2 }
		
 		b10fruBoardManufacturer OBJECT-TYPE
			SYNTAX DisplayString
			MAX-ACCESS read-only
			STATUS current
			DESCRIPTION
				"Used to read the Board Manufacturer from the bladef10 fru."
			::= { blade10FruDescriptionEntry 3 }
		
 		b10fruBoardPartNumber OBJECT-TYPE
			SYNTAX DisplayString
			MAX-ACCESS read-only
			STATUS current
			DESCRIPTION
				"Used to read the Board Part Number from the blade10 fru."
			::= { blade10FruDescriptionEntry 4 }
		
 		b10fruBoardSerialNumber OBJECT-TYPE
			SYNTAX DisplayString
			MAX-ACCESS read-only
			STATUS current
			DESCRIPTION
				"Used to read the Board Serial Number from the blade10 fru."
			::= { blade10FruDescriptionEntry 5 }
		
 		b10fruBoardManufactureDate OBJECT-TYPE
			SYNTAX DisplayString
			MAX-ACCESS read-only
			STATUS current
			DESCRIPTION
				"Used to read the Board Manufacture Date from the blade10 fru."
			::= { blade10FruDescriptionEntry 6 }
		
 		b10fruProductDescription OBJECT-TYPE
			SYNTAX DisplayString
			MAX-ACCESS read-only
			STATUS current
			DESCRIPTION
				"Used to read the Product Description from the blade10 fru."
			::= { blade10FruDescriptionEntry 7 }
		
 		b10fruProductManufacturer OBJECT-TYPE
			SYNTAX DisplayString
			MAX-ACCESS read-only
			STATUS current
			DESCRIPTION
				"Used to read the Product Manufacturer from the blade10 fru."
			::= { blade10FruDescriptionEntry 8 }
		
 		b10fruProductPartNumber OBJECT-TYPE
			SYNTAX DisplayString
			MAX-ACCESS read-only
			STATUS current
			DESCRIPTION
				"Used to read the Product Part Number from the blade10 fru."
			::= { blade10FruDescriptionEntry 9 }
		
 		b10fruProductSerialNumber OBJECT-TYPE
			SYNTAX DisplayString
			MAX-ACCESS read-only
			STATUS current
			DESCRIPTION
				"Used to read the Product Serial Number from the blade10 fru."
			::= { blade10FruDescriptionEntry 10 }
		
 		b10fruProductRevision OBJECT-TYPE
			SYNTAX DisplayString
			MAX-ACCESS read-only
			STATUS current
			DESCRIPTION
				"Used to read the Product Revision from the blade10 fru."
			::= { blade10FruDescriptionEntry 13 }
		
 		b10fruAll OBJECT-TYPE
			SYNTAX DisplayString
			MAX-ACCESS read-only
			STATUS current
			DESCRIPTION
				"Used to read the fru info all."
			::= { blade10FruDescriptionEntry 14 }
		
		blade10CPUTable OBJECT-TYPE
			SYNTAX SEQUENCE OF Blade10CPUEntry
			MAX-ACCESS not-accessible
			STATUS current
			DESCRIPTION
				"A table containing the list of Blade1 FRU information."
			::= { blade10 2006 }
		
		blade10CPUEntry OBJECT-TYPE
			SYNTAX Blade10CPUEntry
			MAX-ACCESS not-accessible
			STATUS current
			DESCRIPTION
				"Information about a particular current FRU."
			INDEX { b10CPUIndex }
			::= { blade10CPUTable 1 }
		
		Blade10CPUEntry ::=
			SEQUENCE { 
				b10CPUIndex
					INTEGER,
				b10CPUMark
					DisplayString,
				b10CPUInfo
					DisplayString,
				b10CPUPresent
					INTEGER,
				b10CPUHealth
					INTEGER,
				b10CPULocation
					DisplayString
			 }

		b10CPUIndex OBJECT-TYPE
			SYNTAX INTEGER
			MAX-ACCESS not-accessible
			STATUS current
			DESCRIPTION
				"CPU INDEX"
			::= { blade10CPUEntry 1 }
		
		b10CPUMark OBJECT-TYPE
			SYNTAX DisplayString
			MAX-ACCESS read-only
			STATUS current
			DESCRIPTION
				"Get the CPU silk-screen."
			::= { blade10CPUEntry 2 }
		
		b10CPUInfo OBJECT-TYPE
			SYNTAX DisplayString
			MAX-ACCESS read-only
			STATUS current
			DESCRIPTION
				"Get the CPU description of vendor, type and frequency."
			::= { blade10CPUEntry 3 }
		
		b10CPUPresent OBJECT-TYPE
			SYNTAX INTEGER
			MAX-ACCESS read-only
			STATUS current
			DESCRIPTION
				"Get the CPU presence status."
			::= { blade10CPUEntry 4 }
		
		b10CPUHealth OBJECT-TYPE
			SYNTAX INTEGER
			MAX-ACCESS read-only
			STATUS current
			DESCRIPTION
				"Get the CPU health status."
			::= { blade10CPUEntry 5 }
		
		b10CPULocation OBJECT-TYPE
			SYNTAX DisplayString
			MAX-ACCESS read-only
			STATUS current
			DESCRIPTION
				"Get the CPU location."
			::= { blade10CPUEntry 6 }
		
		blade10MemoryTable OBJECT-TYPE
			SYNTAX SEQUENCE OF Blade10MemoryEntry
			MAX-ACCESS not-accessible
			STATUS current
			DESCRIPTION
				"A table containing the list of Blade1 FRU information."
			::= { blade10 2007 }
		
		blade10MemoryEntry OBJECT-TYPE
			SYNTAX Blade10MemoryEntry
			MAX-ACCESS not-accessible
			STATUS current
			DESCRIPTION
				"Information about a particular current FRU."
			INDEX { b10MEMIndex }
			::= { blade10MemoryTable 1 }
		
		Blade10MemoryEntry ::=
			SEQUENCE { 
				b10MEMIndex
					INTEGER,
				b10MEMMark
					DisplayString,
				b10MEMInfo
					DisplayString,
				b10MEMPresent
					INTEGER,
				b10MEMHealth
					INTEGER,
				b10MEMLocation
					DisplayString
			 }

		b10MEMIndex OBJECT-TYPE
			SYNTAX INTEGER
			MAX-ACCESS not-accessible
			STATUS current
			DESCRIPTION
				"MEMORY INDEX"
			::= { blade10MemoryEntry 1 }
		
		b10MEMMark OBJECT-TYPE
			SYNTAX DisplayString
			MAX-ACCESS read-only
			STATUS current
			DESCRIPTION
				"Get the memory silk-screen."
			::= { blade10MemoryEntry 2 }
		
		b10MEMInfo OBJECT-TYPE
			SYNTAX DisplayString
			MAX-ACCESS read-only
			STATUS current
			DESCRIPTION
				"Get the memory description of vendor, frequency and capacity."
			::= { blade10MemoryEntry 3 }
		
		b10MEMPresent OBJECT-TYPE
			SYNTAX INTEGER
			MAX-ACCESS read-only
			STATUS current
			DESCRIPTION
				"Get the memory presence status."
			::= { blade10MemoryEntry 4 }
		
		b10MEMHealth OBJECT-TYPE
			SYNTAX INTEGER
			MAX-ACCESS read-only
			STATUS current
			DESCRIPTION
				"Get the memory health status."
			::= { blade10MemoryEntry 5 }
		
		b10MEMLocation OBJECT-TYPE
			SYNTAX DisplayString
			MAX-ACCESS read-only
			STATUS current
			DESCRIPTION
				"Get the memory location."
			::= { blade10MemoryEntry 6 }
		
		blade10MezzTable OBJECT-TYPE
			SYNTAX SEQUENCE OF Blade10MezzEntry
			MAX-ACCESS not-accessible
			STATUS current
			DESCRIPTION
				"A table containing the list of Blade1 FRU information."
			::= { blade10 2008 }
		
		blade10MezzEntry OBJECT-TYPE
			SYNTAX Blade10MezzEntry
			MAX-ACCESS not-accessible
			STATUS current
			DESCRIPTION
				"Information about a particular current FRU."
			INDEX { b10MezzIndex }
			::= { blade10MezzTable 1 }
		
		Blade10MezzEntry ::=
			SEQUENCE { 
				b10MezzIndex
					INTEGER,
				b10MezzMark
					DisplayString,
				b10MezzInfo
					DisplayString,
				b10MezzPresent
					INTEGER,
				b10MezzHealth
					INTEGER,
				b10MezzLocation
					DisplayString,
				b10MezzMac
					DisplayString
			 }

		b10MezzIndex OBJECT-TYPE
			SYNTAX INTEGER
			MAX-ACCESS not-accessible
			STATUS current
			DESCRIPTION
				"MEZZ INDEX"
			::= { blade10MezzEntry 1 }
		
		b10MezzMark OBJECT-TYPE
			SYNTAX DisplayString
			MAX-ACCESS read-only
			STATUS current
			DESCRIPTION
				"Get the MEZZ silk-screen."
			::= { blade10MezzEntry 2 }
		
		b10MezzInfo OBJECT-TYPE
			SYNTAX DisplayString
			MAX-ACCESS read-only
			STATUS current
			DESCRIPTION
				"Get the MEZZ description of type."
			::= { blade10MezzEntry 3 }
		
		b10MezzPresent OBJECT-TYPE
			SYNTAX INTEGER
			MAX-ACCESS read-only
			STATUS current
			DESCRIPTION
				"Get the MEZZ presence status."
			::= { blade10MezzEntry 4 }
		
		b10MezzHealth OBJECT-TYPE
			SYNTAX INTEGER
			MAX-ACCESS read-only
			STATUS current
			DESCRIPTION
				"Get the MEZZ health status."
			::= { blade10MezzEntry 5 }
		
		b10MezzLocation OBJECT-TYPE
			SYNTAX DisplayString
			MAX-ACCESS read-only
			STATUS current
			DESCRIPTION
				"Get the MEZZ location."
			::= { blade10MezzEntry 6 }
		
		b10MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade10MezzEntry 7 }
		
		blade10DiskTable OBJECT-TYPE
			SYNTAX SEQUENCE OF Blade10DiskEntry
			MAX-ACCESS not-accessible
			STATUS current
			DESCRIPTION
				"A table containing the list of Blade1 FRU information."
			::= { blade10 2009 }
		
		blade10DiskEntry OBJECT-TYPE
			SYNTAX Blade10DiskEntry
			MAX-ACCESS not-accessible
			STATUS current
			DESCRIPTION
				"Information about a particular current FRU."
			INDEX { b10DiskIndex }
			::= { blade10DiskTable 1 }
		
		Blade10DiskEntry ::=
			SEQUENCE { 
				b10DiskIndex
					INTEGER,
				b10DiskMark
					DisplayString,
				b10DiskInfo
					DisplayString,
				b10DiskPresent
					INTEGER,
				b10DiskHealth
					INTEGER,
				b10DiskLocation
					DisplayString
			 }

		b10DiskIndex OBJECT-TYPE
			SYNTAX INTEGER
			MAX-ACCESS not-accessible
			STATUS current
			DESCRIPTION
				"DISK INDEX"
			::= { blade10DiskEntry 1 }
		
		b10DiskMark OBJECT-TYPE
			SYNTAX DisplayString
			MAX-ACCESS read-only
			STATUS current
			DESCRIPTION
				"Get the disk silk-screen."
			::= { blade10DiskEntry 2 }
		
		b10DiskInfo OBJECT-TYPE
			SYNTAX DisplayString
			MAX-ACCESS read-only
			STATUS current
			DESCRIPTION
				"Get the disk description of vendor, capacity and speed."
			::= { blade10DiskEntry 3 }
		
		b10DiskPresent OBJECT-TYPE
			SYNTAX INTEGER
			MAX-ACCESS read-only
			STATUS current
			DESCRIPTION
				"Get the disk presence status."
			::= { blade10DiskEntry 4 }
		
		b10DiskHealth OBJECT-TYPE
			SYNTAX INTEGER
			MAX-ACCESS read-only
			STATUS current
			DESCRIPTION
				"Get the disk health status."
			::= { blade10DiskEntry 5 }
		
		b10DiskLocation OBJECT-TYPE
			SYNTAX DisplayString
			MAX-ACCESS read-only
			STATUS current
			DESCRIPTION
				"Get the disk location."
			::= { blade10DiskEntry 6 }
		
		blade10SecretKvmVmmTable OBJECT-TYPE
			SYNTAX SEQUENCE OF Blade10SecretKvmVmmEntry
			MAX-ACCESS not-accessible
			STATUS current
			DESCRIPTION
				"A table containing the list of Blade10 KVM&VMM secret information."
			::= { blade10 2010 }

		blade10SecretKvmVmmEntry OBJECT-TYPE
			SYNTAX Blade10SecretKvmVmmEntry
			MAX-ACCESS not-accessible
			STATUS current
			DESCRIPTION
				"Information about a particular current KVM&VMM."
			INDEX { b10SecretKvmVmmIndex }
			::= { blade10SecretKvmVmmTable 1 }
		Blade10SecretKvmVmmEntry ::=
			SEQUENCE { 
				b10SecretKvmVmmIndex
					INTEGER,
				b10SecretKvmState
					INTEGER,
				b10SecretVmmState
					INTEGER,
				b10MMSecretVmmKey
					DisplayString,
				b10SecretVmmKey
					DisplayString
			 }
		b10SecretKvmVmmIndex OBJECT-TYPE
			SYNTAX INTEGER
			MAX-ACCESS not-accessible
			STATUS current
			DESCRIPTION
				"KVM&VMM INDEX."
			::= { blade10SecretKvmVmmEntry 1 }
		b10SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade10SecretKvmVmmEntry 2 }
		b10SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade10SecretKvmVmmEntry 3 }
		b10MMSecretVmmKey OBJECT-TYPE
			SYNTAX DisplayString
			MAX-ACCESS read-only
			STATUS current
			DESCRIPTION
				"Get the MM secret VMM key."
			::= { blade10SecretKvmVmmEntry 4 }
		b10SecretVmmKey OBJECT-TYPE
			SYNTAX DisplayString
			MAX-ACCESS read-write
			STATUS current
			DESCRIPTION
				"Set the secret VMM key."
			::= { blade10SecretKvmVmmEntry 5 }
		blade11 OBJECT IDENTIFIER ::= { blades 11 }

		
 		b11DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade11 4 }
		
 		b11PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade11 5 }
		
 		b11Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade11 6 }

		
 		b11Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b11Health information about a particular b11Location. 
				This will be one of the following:
				(0-ok, 1-minor, 2-major, 3-majorandminor,4-critical,5-criticalandminor,6-criticalandmajor,7-criticalandmajorandminor)"
			::= { blade11 8 }
		
 		b11HealthEvents OBJECT-TYPE
			SYNTAX DisplayString
			MAX-ACCESS read-only
			STATUS current
			DESCRIPTION
				"Events that contribute to the b11Health of the b11Location.  
				This is a list of events currently happening on the 
				b11Location."
			::= { blade11 9 }
		
 		b11ClearSEL OBJECT-TYPE
			SYNTAX INTEGER { clear(1) }
			MAX-ACCESS read-write
			STATUS current
			DESCRIPTION
				"Clean the BMC's SEL on the board."
			::= { blade11 12 }
		
 		b11ExDiskBoardPresence OBJECT-TYPE
			SYNTAX INTEGER
				{
				not-present(0),
				present(1)
				}
			MAX-ACCESS read-only
			STATUS current
			DESCRIPTION
				"Used to find out if the extended disk board is present.
				0 - not present
				1 - present"
			::= { blade11 14 }
		
 		b11BladeVersion OBJECT-TYPE
			SYNTAX DisplayString
			MAX-ACCESS read-only
			STATUS current
			DESCRIPTION
				"display the Version of board11."
			::= { blade11 20 }
		
 		b11MACAddress OBJECT-TYPE
			SYNTAX DisplayString
			MAX-ACCESS read-only
			STATUS current
			DESCRIPTION
				"display the MACAddress of board11."
			::= { blade11 21 }
		
				
							
		
 		b11Safepwofftime OBJECT-TYPE
			SYNTAX INTEGER
			MAX-ACCESS read-write
			STATUS current
			DESCRIPTION
				"the safe poweroff time.
				"
			::= { blade11 26 }
		
 		b11BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade11 32 }
		
 		b11Systeminfo OBJECT-TYPE
			SYNTAX DisplayString
			MAX-ACCESS read-write
			STATUS current
			DESCRIPTION
				"display the system information of board11."
			::= { blade11 36 }

		
 		b11SystemProperties OBJECT-TYPE
			SYNTAX DisplayString
			MAX-ACCESS read-only
			STATUS current
			DESCRIPTION
				"Get the power of blade1."
			::= { blade11 39 }
		
 		b11BiosCfg OBJECT-TYPE
			SYNTAX DisplayString
			MAX-ACCESS read-write
			STATUS current
			DESCRIPTION
				"Get the power of blade1."
			::= { blade11 40 }
		
 		b11WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade11 41 }
		
 		b11RealTimePower OBJECT-TYPE
			SYNTAX INTEGER
			MAX-ACCESS read-only
			STATUS current
			DESCRIPTION
				" "
			::= { blade11 43 }
		
 		b11PowerCapping OBJECT-TYPE
			SYNTAX DisplayString
			MAX-ACCESS read-write
			STATUS current
			DESCRIPTION
				" "
			::= { blade11 44 }
		
 		b11Powerreference OBJECT-TYPE
			SYNTAX INTEGER
			MAX-ACCESS read-only
			STATUS current
			DESCRIPTION
				" "
			::= { blade11 45 }
		
 		b11ClearBiosConfig OBJECT-TYPE
			SYNTAX INTEGER
			MAX-ACCESS read-write
			STATUS current
			DESCRIPTION
				" "
			::= { blade11 46 }
		
 		b11BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade11 47 }
		
 		b11BmcUserAdd OBJECT-TYPE
			SYNTAX DisplayString
			MAX-ACCESS read-write
			STATUS current
			DESCRIPTION
				"Used to Add the BMC User
				settable format:
				username,passwd"
			::= { blade11 48 }
		
 		b11BmcUserDel OBJECT-TYPE
			SYNTAX DisplayString
			MAX-ACCESS read-write
			STATUS current
			DESCRIPTION
				"Used to Del the BMC User
				settable format:
				username"
			::= { blade11 49 }
		
 		b11BmcUserPasswd OBJECT-TYPE
			SYNTAX DisplayString
			MAX-ACCESS read-write
			STATUS current
			DESCRIPTION
				"Used to Change the BMC User Passwd
				settable format:
				username,passwd"
			::= { blade11 50 }
		
 		b11BmcUserpropertychg OBJECT-TYPE
			SYNTAX DisplayString
			MAX-ACCESS read-write
			STATUS current
			DESCRIPTION
				"Used to Change the BMC User Property
				settable format:
				username,property"
			::= { blade11 51 }
		
 		b11BmcGateway OBJECT-TYPE
			SYNTAX DisplayString
			MAX-ACCESS read-write
			STATUS current
			DESCRIPTION
				"Read or set the gateway."
			::= { blade11 52 }
		
 		b11SlotBitmap OBJECT-TYPE
			SYNTAX INTEGER
			MAX-ACCESS read-only
			STATUS current
			DESCRIPTION
				" "
			::= { blade11 55 }
		
		b11systemGuid OBJECT-TYPE
			SYNTAX DisplayString
			MAX-ACCESS read-only
			STATUS current
			DESCRIPTION
				" "
			::= { blade11 56 }
		
		b11ProductName OBJECT-TYPE
			SYNTAX DisplayString
			MAX-ACCESS read-only
			STATUS current
			DESCRIPTION
				"display the Version of board11."
			::= { blade11 57 }

		b11BundleVersion OBJECT-TYPE
			SYNTAX DisplayString
			MAX-ACCESS read-write
			STATUS current
			DESCRIPTION
				"Get or set the board11 bundle version."
			::= { blade11 58 }

 		blade11SensorTargetTable OBJECT-TYPE
			SYNTAX SEQUENCE OF Blade11SensorTargetEntry
			MAX-ACCESS not-accessible
			STATUS current
			DESCRIPTION
				"A table containing the list of sensor information."
			::= { blade11 2001 }
		
 		blade11SensorTargetEntry OBJECT-TYPE
			SYNTAX Blade11SensorTargetEntry
			MAX-ACCESS not-accessible
			STATUS current
			DESCRIPTION
				"Information about a particular current sensor."
			INDEX { b11Target }
			::= { blade11SensorTargetTable 1 }
		
		Blade11SensorTargetEntry ::=
			SEQUENCE { 
				b11Target
					DisplayString,
				b11Current
					DisplayString,
				b11ThresholdsAll
					DisplayString,
				b11UpperCritical
					DisplayString,
				b11UpperNonCritical
					DisplayString,
				b11UpperNonRecoverable
					DisplayString,
				b11LowerNonCritical
					DisplayString,
				b11LowerCritical
					DisplayString,
				b11LowerNonRecoverable
					DisplayString,
				b11SensorHealth
					INTEGER,
				b11SensorHealthEvents
					DisplayString,
				b11NegativeHysteresis
					DisplayString,
				b11PositiveHysteresis
					DisplayString,
				b11SensorType
					DisplayString,
				b11SensorFRUInfo
					DisplayString
			 }

 		b11Target OBJECT-TYPE
			SYNTAX DisplayString
			MAX-ACCESS not-accessible
			STATUS current
			DESCRIPTION
				"sensor Name"
			::= { blade11SensorTargetEntry 1 }
		
 		b11Current OBJECT-TYPE
			SYNTAX DisplayString
			MAX-ACCESS read-only
			STATUS current
			DESCRIPTION
				"Display the current value of a sensor."
			::= { blade11SensorTargetEntry 2 }
		
 		b11ThresholdsAll OBJECT-TYPE
			SYNTAX DisplayString
			MAX-ACCESS read-only
			STATUS current
			DESCRIPTION
				"All thresholds of a sensor"
			::= { blade11SensorTargetEntry 3 }
		
 		b11UpperCritical OBJECT-TYPE
			SYNTAX DisplayString
			MAX-ACCESS read-write
			STATUS current
			DESCRIPTION
				"Upper critical thresholds"
			::= { blade11SensorTargetEntry 4 }
		
 		b11UpperNonCritical OBJECT-TYPE
			SYNTAX DisplayString
			MAX-ACCESS read-write
			STATUS current
			DESCRIPTION
				"Upper non-critical thresholds"
			::= { blade11SensorTargetEntry 5 }
		
 		b11UpperNonRecoverable OBJECT-TYPE
			SYNTAX DisplayString
			MAX-ACCESS read-write
			STATUS current
			DESCRIPTION
				"Upper non-recoverable thresholds"
			::= { blade11SensorTargetEntry 6 }
		
 		b11LowerNonCritical OBJECT-TYPE
			SYNTAX DisplayString
			MAX-ACCESS read-write
			STATUS current
			DESCRIPTION
				"Lower non-critical thresholds"
			::= { blade11SensorTargetEntry 7 }
		
 		b11LowerCritical OBJECT-TYPE
			SYNTAX DisplayString
			MAX-ACCESS read-write
			STATUS current
			DESCRIPTION
				"Lower critical thresholds"
			::= { blade11SensorTargetEntry 8 }
		
 		b11LowerNonRecoverable OBJECT-TYPE
			SYNTAX DisplayString
			MAX-ACCESS read-write
			STATUS current
			DESCRIPTION
				"Lower non-recoverable thresholds"
			::= { blade11SensorTargetEntry 9 }
		
 		b11SensorHealth OBJECT-TYPE
			SYNTAX INTEGER
				{
				ok(0),
				minor(1),
				major(2),
				critical(3)
				}
			MAX-ACCESS read-only
			STATUS current
			DESCRIPTION
				"b11Health information about a particular b11Location. 
				This will be one of the following:
				(0-ok, 1-minor, 2-major, 3-critical)"
			::= { blade11SensorTargetEntry 10 }
		
 		b11SensorHealthEvents OBJECT-TYPE
			SYNTAX DisplayString
			MAX-ACCESS read-only
			STATUS current
			DESCRIPTION
				"Events that contribute to the b11Health of the b11Location.  
				This is a list of events currently happening on the 
				b11Location."
			::= { blade11SensorTargetEntry 11 }
		
		
 		b11NegativeHysteresis OBJECT-TYPE
			SYNTAX DisplayString
			MAX-ACCESS read-write
			STATUS current
			DESCRIPTION
				"Get/Set the negativeHysteresis value"
			::= { blade11SensorTargetEntry 16 }
		
 		b11PositiveHysteresis OBJECT-TYPE
			SYNTAX DisplayString
			MAX-ACCESS read-write
			STATUS current
			DESCRIPTION
				"Get/Set the positiveHysteresis value."
			::= { blade11SensorTargetEntry 17 }
		
 		b11SensorType OBJECT-TYPE
			SYNTAX DisplayString
			MAX-ACCESS read-only
			STATUS current
			DESCRIPTION
				"Get the type of the sensor."
			::= { blade11SensorTargetEntry 18 }
		
 		b11SensorFRUInfo OBJECT-TYPE
			SYNTAX DisplayString
			MAX-ACCESS read-only
			STATUS current
			DESCRIPTION
				"Get the fruinfo of the sensor."
			::= { blade11SensorTargetEntry 19 }
		
 		blade11FruTable OBJECT-TYPE
			SYNTAX SEQUENCE OF Blade11FruEntry
			MAX-ACCESS not-accessible
			STATUS current
			DESCRIPTION
				"A table containing the list of FRU information."
			::= { blade11 2002 }
		
 		blade11FruEntry OBJECT-TYPE
			SYNTAX Blade11FruEntry
			MAX-ACCESS not-accessible
			STATUS current
			DESCRIPTION
				"Information about a particular current FRU."
			INDEX { b11fruNumber }
			::= { blade11FruTable 1 }
		
		Blade11FruEntry ::=
			SEQUENCE { 
				b11fruNumber
					INTEGER,
				b11FruHotSwapState
					DisplayString,
				b11FruLedProperties
					DisplayString,
				b11FRUControl
					INTEGER,
				b11FRULabel
					DisplayString,
				b11ResetReason
					DisplayString
			 }

 		b11fruNumber OBJECT-TYPE
			SYNTAX INTEGER
			MAX-ACCESS not-accessible
			STATUS current
			DESCRIPTION
				" "
			::= { blade11FruEntry 1 }
		
 		b11FruHotSwapState OBJECT-TYPE
			SYNTAX DisplayString
			MAX-ACCESS read-only
			STATUS current
			DESCRIPTION
				"Retrieve the hot swap state of the FRU from the 
				internally known hot swap states of blade11."
			::= { blade11FruEntry 3 }
		
 		b11FruLedProperties OBJECT-TYPE
			SYNTAX DisplayString
			MAX-ACCESS read-only
			STATUS current
			DESCRIPTION
				"Retrieves the LED support information from a FRU. Returns a comma separated
				list of LEDS and the number of FRU supported user LEDs."
			::= { blade11FruEntry 4 }

		

		b11FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade11FruEntry 9 }
		
 		b11FRULabel OBJECT-TYPE
			SYNTAX DisplayString
			MAX-ACCESS read-only
			STATUS current
			DESCRIPTION
				"Get fru label of blade11."
			::= { blade11FruEntry 10 }
		
 		b11ResetReason OBJECT-TYPE
			SYNTAX DisplayString
			MAX-ACCESS read-only
			STATUS current
			DESCRIPTION
				"Delete fru label of smm."
			::= { blade11FruEntry 11 }
		
 		blade11FruLedTable OBJECT-TYPE
			SYNTAX SEQUENCE OF Blade11FruLedEntry
			MAX-ACCESS not-accessible
			STATUS current
			DESCRIPTION
				"A table containing the list of led information."
			::= { blade11 2003 }
		
 		blade11FruLedEntry OBJECT-TYPE
			SYNTAX Blade11FruLedEntry
			MAX-ACCESS not-accessible
			STATUS current
			DESCRIPTION
				"Information about a particular current led."
			INDEX { b11FruID, b11FruLed }
			::= { blade11FruLedTable 1 }
		
		Blade11FruLedEntry ::=
			SEQUENCE { 
				b11FruID
					INTEGER,
				b11FruLed
					DisplayString,
				b11FruLedColorProps
					DisplayString,
				b11FruLedState
					DisplayString
			 }

 		b11FruID OBJECT-TYPE
			SYNTAX INTEGER
			MAX-ACCESS not-accessible
			STATUS current
			DESCRIPTION
				" "
			::= { blade11FruLedEntry 1 }
		
 		b11FruLed OBJECT-TYPE
			SYNTAX DisplayString
			MAX-ACCESS not-accessible
			STATUS current
			DESCRIPTION
				" "
			::= { blade11FruLedEntry 2 }
		
 		b11FruLedColorProps OBJECT-TYPE
			SYNTAX DisplayString
			MAX-ACCESS read-only
			STATUS current
			DESCRIPTION
				"Finds out what colors are supported by the LED"
			::= { blade11FruLedEntry 3 }
		
 		b11FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade11FruLedEntry 4 }
		
 		blade11FruDescriptionTable OBJECT-TYPE
			SYNTAX SEQUENCE OF Blade11FruDescriptionEntry
			MAX-ACCESS not-accessible
			STATUS current
			DESCRIPTION
				"A table containing the list of blade11 FRU information."
			::= { blade11 2004 }
		
 		blade11FruDescriptionEntry OBJECT-TYPE
			SYNTAX Blade11FruDescriptionEntry
			MAX-ACCESS not-accessible
			STATUS current
			DESCRIPTION
				"Information about a particular current FRU."
			INDEX { b11fruNum }
			::= { blade11FruDescriptionTable 1 }
		
		Blade11FruDescriptionEntry ::=
			SEQUENCE { 
				b11fruNum
					INTEGER,
				b11fruBoardDescription
					DisplayString,
				b11fruBoardManufacturer
					DisplayString,
				b11fruBoardPartNumber
					DisplayString,
				b11fruBoardSerialNumber
					DisplayString,
				b11fruBoardManufactureDate
					DisplayString,
				b11fruProductDescription
					DisplayString,
				b11fruProductManufacturer
					DisplayString,
				b11fruProductPartNumber
					DisplayString,
				b11fruProductSerialNumber
					DisplayString,
				b11fruProductRevision
					DisplayString,
				b11fruAll
					DisplayString
			 }

 		b11fruNum OBJECT-TYPE
			SYNTAX INTEGER
			MAX-ACCESS not-accessible
			STATUS current
			DESCRIPTION
				"blade11 FRU's INDEX"
			::= { blade11FruDescriptionEntry 1 }
		
 		b11fruBoardDescription OBJECT-TYPE
			SYNTAX DisplayString
			MAX-ACCESS read-only
			STATUS current
			DESCRIPTION
				"Used to read the Board Description from the blade11 fru."
			::= { blade11FruDescriptionEntry 2 }
		
 		b11fruBoardManufacturer OBJECT-TYPE
			SYNTAX DisplayString
			MAX-ACCESS read-only
			STATUS current
			DESCRIPTION
				"Used to read the Board Manufacturer from the bladef11 fru."
			::= { blade11FruDescriptionEntry 3 }
		
 		b11fruBoardPartNumber OBJECT-TYPE
			SYNTAX DisplayString
			MAX-ACCESS read-only
			STATUS current
			DESCRIPTION
				"Used to read the Board Part Number from the blade11 fru."
			::= { blade11FruDescriptionEntry 4 }
		
 		b11fruBoardSerialNumber OBJECT-TYPE
			SYNTAX DisplayString
			MAX-ACCESS read-only
			STATUS current
			DESCRIPTION
				"Used to read the Board Serial Number from the blade11 fru."
			::= { blade11FruDescriptionEntry 5 }
		
 		b11fruBoardManufactureDate OBJECT-TYPE
			SYNTAX DisplayString
			MAX-ACCESS read-only
			STATUS current
			DESCRIPTION
				"Used to read the Board Manufacture Date from the blade11 fru."
			::= { blade11FruDescriptionEntry 6 }
		
 		b11fruProductDescription OBJECT-TYPE
			SYNTAX DisplayString
			MAX-ACCESS read-only
			STATUS current
			DESCRIPTION
				"Used to read the Product Description from the blade11 fru."
			::= { blade11FruDescriptionEntry 7 }
		
 		b11fruProductManufacturer OBJECT-TYPE
			SYNTAX DisplayString
			MAX-ACCESS read-only
			STATUS current
			DESCRIPTION
				"Used to read the Product Manufacturer from the blade11 fru."
			::= { blade11FruDescriptionEntry 8 }
		
 		b11fruProductPartNumber OBJECT-TYPE
			SYNTAX DisplayString
			MAX-ACCESS read-only
			STATUS current
			DESCRIPTION
				"Used to read the Product Part Number from the blade11 fru."
			::= { blade11FruDescriptionEntry 9 }
		
 		b11fruProductSerialNumber OBJECT-TYPE
			SYNTAX DisplayString
			MAX-ACCESS read-only
			STATUS current
			DESCRIPTION
				"Used to read the Product Serial Number from the blade11 fru."
			::= { blade11FruDescriptionEntry 10 }
		
 		b11fruProductRevision OBJECT-TYPE
			SYNTAX DisplayString
			MAX-ACCESS read-only
			STATUS current
			DESCRIPTION
				"Used to read the Product Revision from the blade11 fru."
			::= { blade11FruDescriptionEntry 13 }
		
 		b11fruAll OBJECT-TYPE
			SYNTAX DisplayString
			MAX-ACCESS read-only
			STATUS current
			DESCRIPTION
				"Used to read the fru info all."
			::= { blade11FruDescriptionEntry 14 }
		
		blade11CPUTable OBJECT-TYPE
			SYNTAX SEQUENCE OF Blade11CPUEntry
			MAX-ACCESS not-accessible
			STATUS current
			DESCRIPTION
				"A table containing the list of Blade1 FRU information."
			::= { blade11 2006 }
		
		blade11CPUEntry OBJECT-TYPE
			SYNTAX Blade11CPUEntry
			MAX-ACCESS not-accessible
			STATUS current
			DESCRIPTION
				"Information about a particular current FRU."
			INDEX { b11CPUIndex }
			::= { blade11CPUTable 1 }
		
		Blade11CPUEntry ::=
			SEQUENCE { 
				b11CPUIndex
					INTEGER,
				b11CPUMark
					DisplayString,
				b11CPUInfo
					DisplayString,
				b11CPUPresent
					INTEGER,
				b11CPUHealth
					INTEGER,
				b11CPULocation
					DisplayString
			 }

		b11CPUIndex OBJECT-TYPE
			SYNTAX INTEGER
			MAX-ACCESS not-accessible
			STATUS current
			DESCRIPTION
				"CPU INDEX"
			::= { blade11CPUEntry 1 }
		
		b11CPUMark OBJECT-TYPE
			SYNTAX DisplayString
			MAX-ACCESS read-only
			STATUS current
			DESCRIPTION
				"Get the CPU silk-screen."
			::= { blade11CPUEntry 2 }
		
		b11CPUInfo OBJECT-TYPE
			SYNTAX DisplayString
			MAX-ACCESS read-only
			STATUS current
			DESCRIPTION
				"Get the CPU description of vendor, type and frequency."
			::= { blade11CPUEntry 3 }
		
		b11CPUPresent OBJECT-TYPE
			SYNTAX INTEGER
			MAX-ACCESS read-only
			STATUS current
			DESCRIPTION
				"Get the CPU presence status."
			::= { blade11CPUEntry 4 }
		
		b11CPUHealth OBJECT-TYPE
			SYNTAX INTEGER
			MAX-ACCESS read-only
			STATUS current
			DESCRIPTION
				"Get the CPU health status."
			::= { blade11CPUEntry 5 }
		
		b11CPULocation OBJECT-TYPE
			SYNTAX DisplayString
			MAX-ACCESS read-only
			STATUS current
			DESCRIPTION
				"Get the CPU location."
			::= { blade11CPUEntry 6 }
		
		blade11MemoryTable OBJECT-TYPE
			SYNTAX SEQUENCE OF Blade11MemoryEntry
			MAX-ACCESS not-accessible
			STATUS current
			DESCRIPTION
				"A table containing the list of Blade1 FRU information."
			::= { blade11 2007 }
		
		blade11MemoryEntry OBJECT-TYPE
			SYNTAX Blade11MemoryEntry
			MAX-ACCESS not-accessible
			STATUS current
			DESCRIPTION
				"Information about a particular current FRU."
			INDEX { b11MEMIndex }
			::= { blade11MemoryTable 1 }
		
		Blade11MemoryEntry ::=
			SEQUENCE { 
				b11MEMIndex
					INTEGER,
				b11MEMMark
					DisplayString,
				b11MEMInfo
					DisplayString,
				b11MEMPresent
					INTEGER,
				b11MEMHealth
					INTEGER,
				b11MEMLocation
					DisplayString
			 }

		b11MEMIndex OBJECT-TYPE
			SYNTAX INTEGER
			MAX-ACCESS not-accessible
			STATUS current
			DESCRIPTION
				"MEMORY INDEX"
			::= { blade11MemoryEntry 1 }
		
		b11MEMMark OBJECT-TYPE
			SYNTAX DisplayString
			MAX-ACCESS read-only
			STATUS current
			DESCRIPTION
				"Get the memory silk-screen."
			::= { blade11MemoryEntry 2 }
		
		b11MEMInfo OBJECT-TYPE
			SYNTAX DisplayString
			MAX-ACCESS read-only
			STATUS current
			DESCRIPTION
				"Get the memory description of vendor, frequency and capacity."
			::= { blade11MemoryEntry 3 }
		
		b11MEMPresent OBJECT-TYPE
			SYNTAX INTEGER
			MAX-ACCESS read-only
			STATUS current
			DESCRIPTION
				"Get the memory presence status."
			::= { blade11MemoryEntry 4 }
		
		b11MEMHealth OBJECT-TYPE
			SYNTAX INTEGER
			MAX-ACCESS read-only
			STATUS current
			DESCRIPTION
				"Get the memory health status."
			::= { blade11MemoryEntry 5 }
		
		b11MEMLocation OBJECT-TYPE
			SYNTAX DisplayString
			MAX-ACCESS read-only
			STATUS current
			DESCRIPTION
				"Get the memory location."
			::= { blade11MemoryEntry 6 }
		
		blade11MezzTable OBJECT-TYPE
			SYNTAX SEQUENCE OF Blade11MezzEntry
			MAX-ACCESS not-accessible
			STATUS current
			DESCRIPTION
				"A table containing the list of Blade1 FRU information."
			::= { blade11 2008 }
		
		blade11MezzEntry OBJECT-TYPE
			SYNTAX Blade11MezzEntry
			MAX-ACCESS not-accessible
			STATUS current
			DESCRIPTION
				"Information about a particular current FRU."
			INDEX { b11MezzIndex }
			::= { blade11MezzTable 1 }
		
		Blade11MezzEntry ::=
			SEQUENCE { 
				b11MezzIndex
					INTEGER,
				b11MezzMark
					DisplayString,
				b11MezzInfo
					DisplayString,
				b11MezzPresent
					INTEGER,
				b11MezzHealth
					INTEGER,
				b11MezzLocation
					DisplayString,
				b11MezzMac
					DisplayString
			 }

		b11MezzIndex OBJECT-TYPE
			SYNTAX INTEGER
			MAX-ACCESS not-accessible
			STATUS current
			DESCRIPTION
				"MEZZ INDEX"
			::= { blade11MezzEntry 1 }
		
		b11MezzMark OBJECT-TYPE
			SYNTAX DisplayString
			MAX-ACCESS read-only
			STATUS current
			DESCRIPTION
				"Get the MEZZ silk-screen."
			::= { blade11MezzEntry 2 }
		
		b11MezzInfo OBJECT-TYPE
			SYNTAX DisplayString
			MAX-ACCESS read-only
			STATUS current
			DESCRIPTION
				"Get the MEZZ description of type."
			::= { blade11MezzEntry 3 }
		
		b11MezzPresent OBJECT-TYPE
			SYNTAX INTEGER
			MAX-ACCESS read-only
			STATUS current
			DESCRIPTION
				"Get the MEZZ presence status."
			::= { blade11MezzEntry 4 }
		
		b11MezzHealth OBJECT-TYPE
			SYNTAX INTEGER
			MAX-ACCESS read-only
			STATUS current
			DESCRIPTION
				"Get the MEZZ health status."
			::= { blade11MezzEntry 5 }
		
		b11MezzLocation OBJECT-TYPE
			SYNTAX DisplayString
			MAX-ACCESS read-only
			STATUS current
			DESCRIPTION
				"Get the MEZZ location."
			::= { blade11MezzEntry 6 }
		
		b11MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade11MezzEntry 7 }
		
		blade11DiskTable OBJECT-TYPE
			SYNTAX SEQUENCE OF Blade11DiskEntry
			MAX-ACCESS not-accessible
			STATUS current
			DESCRIPTION
				"A table containing the list of Blade1 FRU information."
			::= { blade11 2009 }
		
		blade11DiskEntry OBJECT-TYPE
			SYNTAX Blade11DiskEntry
			MAX-ACCESS not-accessible
			STATUS current
			DESCRIPTION
				"Information about a particular current FRU."
			INDEX { b11DiskIndex }
			::= { blade11DiskTable 1 }
		
		Blade11DiskEntry ::=
			SEQUENCE { 
				b11DiskIndex
					INTEGER,
				b11DiskMark
					DisplayString,
				b11DiskInfo
					DisplayString,
				b11DiskPresent
					INTEGER,
				b11DiskHealth
					INTEGER,
				b11DiskLocation
					DisplayString
			 }

		b11DiskIndex OBJECT-TYPE
			SYNTAX INTEGER
			MAX-ACCESS not-accessible
			STATUS current
			DESCRIPTION
				"DISK INDEX"
			::= { blade11DiskEntry 1 }
		
		b11DiskMark OBJECT-TYPE
			SYNTAX DisplayString
			MAX-ACCESS read-only
			STATUS current
			DESCRIPTION
				"Get the disk silk-screen."
			::= { blade11DiskEntry 2 }
		
		b11DiskInfo OBJECT-TYPE
			SYNTAX DisplayString
			MAX-ACCESS read-only
			STATUS current
			DESCRIPTION
				"Get the disk description of vendor, capacity and speed."
			::= { blade11DiskEntry 3 }
		
		b11DiskPresent OBJECT-TYPE
			SYNTAX INTEGER
			MAX-ACCESS read-only
			STATUS current
			DESCRIPTION
				"Get the disk presence status."
			::= { blade11DiskEntry 4 }
		
		b11DiskHealth OBJECT-TYPE
			SYNTAX INTEGER
			MAX-ACCESS read-only
			STATUS current
			DESCRIPTION
				"Get the disk health status."
			::= { blade11DiskEntry 5 }
		
		b11DiskLocation OBJECT-TYPE
			SYNTAX DisplayString
			MAX-ACCESS read-only
			STATUS current
			DESCRIPTION
				"Get the disk location."
			::= { blade11DiskEntry 6 }
		
		blade11SecretKvmVmmTable OBJECT-TYPE
			SYNTAX SEQUENCE OF Blade11SecretKvmVmmEntry
			MAX-ACCESS not-accessible
			STATUS current
			DESCRIPTION
				"A table containing the list of Blade11 KVM&VMM secret information."
			::= { blade11 2010 }

		blade11SecretKvmVmmEntry OBJECT-TYPE
			SYNTAX Blade11SecretKvmVmmEntry
			MAX-ACCESS not-accessible
			STATUS current
			DESCRIPTION
				"Information about a particular current KVM&VMM."
			INDEX { b11SecretKvmVmmIndex }
			::= { blade11SecretKvmVmmTable 1 }
		Blade11SecretKvmVmmEntry ::=
			SEQUENCE { 
				b11SecretKvmVmmIndex
					INTEGER,
				b11SecretKvmState
					INTEGER,
				b11SecretVmmState
					INTEGER,
				b11MMSecretVmmKey
					DisplayString,
				b11SecretVmmKey
					DisplayString
			 }
		b11SecretKvmVmmIndex OBJECT-TYPE
			SYNTAX INTEGER
			MAX-ACCESS not-accessible
			STATUS current
			DESCRIPTION
				"KVM&VMM INDEX."
			::= { blade11SecretKvmVmmEntry 1 }

		
		b11SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade11SecretKvmVmmEntry 2 }
		b11SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade11SecretKvmVmmEntry 3 }
		b11MMSecretVmmKey OBJECT-TYPE
			SYNTAX DisplayString
			MAX-ACCESS read-only
			STATUS current
			DESCRIPTION
				"Get the MM secret VMM key."
			::= { blade11SecretKvmVmmEntry 4 }
		b11SecretVmmKey OBJECT-TYPE
			SYNTAX DisplayString
			MAX-ACCESS read-write
			STATUS current
			DESCRIPTION
				"Set the secret VMM key."
			::= { blade11SecretKvmVmmEntry 5 }
		blade12 OBJECT IDENTIFIER ::= { blades 12 }

		
 		b12DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade12 4 }
		
 		b12PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade12 5 }
		
 		b12Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade12 6 }

		
 		b12Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b12Health information about a particular b12Location. 
				This will be one of the following:
				(0-ok, 1-minor, 2-major, 3-majorandminor,4-critical,5-criticalandminor,6-criticalandmajor,7-criticalandmajorandminor)"
			::= { blade12 8 }
		
 		b12HealthEvents OBJECT-TYPE
			SYNTAX DisplayString
			MAX-ACCESS read-only
			STATUS current
			DESCRIPTION
				"Events that contribute to the b12Health of the b12Location.  
				This is a list of events currently happening on the 
				b12Location."
			::= { blade12 9 }
		
 		b12ClearSEL OBJECT-TYPE
			SYNTAX INTEGER { clear(1) }
			MAX-ACCESS read-write
			STATUS current
			DESCRIPTION
				"Clean the BMC's SEL on the board."
			::= { blade12 12 }
		
 		b12ExDiskBoardPresence OBJECT-TYPE
			SYNTAX INTEGER
				{
				not-present(0),
				present(1)
				}
			MAX-ACCESS read-only
			STATUS current
			DESCRIPTION
				"Used to find out if the extended disk board is present.
				0 - not present
				1 - present"
			::= { blade12 14 }
		
 		b12BladeVersion OBJECT-TYPE
			SYNTAX DisplayString
			MAX-ACCESS read-only
			STATUS current
			DESCRIPTION
				"display the Version of board12."
			::= { blade12 20 }
		
 		b12MACAddress OBJECT-TYPE
			SYNTAX DisplayString
			MAX-ACCESS read-only
			STATUS current
			DESCRIPTION
				"display the MACAddress of board12."
			::= { blade12 21 }
		
		
 		b12Safepwofftime OBJECT-TYPE
			SYNTAX INTEGER
			MAX-ACCESS read-write
			STATUS current
			DESCRIPTION
				"the safe poweroff time.
				"
			::= { blade12 26 }
		
 		b12BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]      
				6=Force boot into BIOS Setup
				15=Force boot from Floppy/primary removable media           
				
				"
			::= { blade12 32 }
		
 		b12Systeminfo OBJECT-TYPE
			SYNTAX DisplayString
			MAX-ACCESS read-write
			STATUS current
			DESCRIPTION
				"display the system information of board12."
			::= { blade12 36 }

		
 		b12SystemProperties OBJECT-TYPE
			SYNTAX DisplayString
			MAX-ACCESS read-only
			STATUS current
			DESCRIPTION
				"Get the power of blade1."
			::= { blade12 39 }
		
 		b12BiosCfg OBJECT-TYPE
			SYNTAX DisplayString
			MAX-ACCESS read-write
			STATUS current
			DESCRIPTION
				"Get the power of blade1."
			::= { blade12 40 }
		
 		b12WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade12 41 }
		
 		b12RealTimePower OBJECT-TYPE
			SYNTAX INTEGER
			MAX-ACCESS read-only
			STATUS current
			DESCRIPTION
				" "
			::= { blade12 43 }
		
 		b12PowerCapping OBJECT-TYPE
			SYNTAX DisplayString
			MAX-ACCESS read-write
			STATUS current
			DESCRIPTION
				" "
			::= { blade12 44 }
		
 		b12Powerreference OBJECT-TYPE
			SYNTAX INTEGER
			MAX-ACCESS read-only
			STATUS current
			DESCRIPTION
				" "
			::= { blade12 45 }
		
 		b12ClearBiosConfig OBJECT-TYPE
			SYNTAX INTEGER
			MAX-ACCESS read-write
			STATUS current
			DESCRIPTION
				" "
			::= { blade12 46 }
		
 		b12BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade12 47 }
		
 		b12BmcUserAdd OBJECT-TYPE
			SYNTAX DisplayString
			MAX-ACCESS read-write
			STATUS current
			DESCRIPTION
				"Used to Add the BMC User
				settable format:
				username,passwd"
			::= { blade12 48 }
		
 		b12BmcUserDel OBJECT-TYPE
			SYNTAX DisplayString
			MAX-ACCESS read-write
			STATUS current
			DESCRIPTION
				"Used to Del the BMC User
				settable format:
				username"
			::= { blade12 49 }
		
 		b12BmcUserPasswd OBJECT-TYPE
			SYNTAX DisplayString
			MAX-ACCESS read-write
			STATUS current
			DESCRIPTION
				"Used to Change the BMC User Passwd
				settable format:
				username,passwd"
			::= { blade12 50 }
		
 		b12BmcUserpropertychg OBJECT-TYPE
			SYNTAX DisplayString
			MAX-ACCESS read-write
			STATUS current
			DESCRIPTION
				"Used to Change the BMC User Property
				settable format:
				username,property"
			::= { blade12 51 }
		
 		b12BmcGateway OBJECT-TYPE
			SYNTAX DisplayString
			MAX-ACCESS read-write
			STATUS current
			DESCRIPTION
				"Read or set the gateway."
			::= { blade12 52 }
		
 		b12SlotBitmap OBJECT-TYPE
			SYNTAX INTEGER
			MAX-ACCESS read-only
			STATUS current
			DESCRIPTION
				" "
			::= { blade12 55 }
		
		b12systemGuid OBJECT-TYPE
			SYNTAX DisplayString
			MAX-ACCESS read-only
			STATUS current
			DESCRIPTION
				" "
			::= { blade12 56 }
		
		b12ProductName OBJECT-TYPE
			SYNTAX DisplayString
			MAX-ACCESS read-only
			STATUS current
			DESCRIPTION
				"display the Version of board12."
			::= { blade12 57 }
		
		b12BundleVersion OBJECT-TYPE
			SYNTAX DisplayString
			MAX-ACCESS read-write
			STATUS current
			DESCRIPTION
				"Get or set the board12 bundle version."
			::= { blade12 58 }

 		blade12SensorTargetTable OBJECT-TYPE
			SYNTAX SEQUENCE OF Blade12SensorTargetEntry
			MAX-ACCESS not-accessible
			STATUS current
			DESCRIPTION
				"A table containing the list of sensor information."
			::= { blade12 2001 }
		
 		blade12SensorTargetEntry OBJECT-TYPE
			SYNTAX Blade12SensorTargetEntry
			MAX-ACCESS not-accessible
			STATUS current
			DESCRIPTION
				"Information about a particular current sensor."
			INDEX { b12Target }
			::= { blade12SensorTargetTable 1 }
		
		Blade12SensorTargetEntry ::=
			SEQUENCE { 
				b12Target
					DisplayString,
				b12Current
					DisplayString,
				b12ThresholdsAll
					DisplayString,
				b12UpperCritical
					DisplayString,
				b12UpperNonCritical
					DisplayString,
				b12UpperNonRecoverable
					DisplayString,
				b12LowerNonCritical
					DisplayString,
				b12LowerCritical
					DisplayString,
				b12LowerNonRecoverable
					DisplayString,
				b12SensorHealth
					INTEGER,
				b12SensorHealthEvents
					DisplayString,
				b12NegativeHysteresis
					DisplayString,
				b12PositiveHysteresis
					DisplayString,
				b12SensorType
					DisplayString,
				b12SensorFRUInfo
					DisplayString
			 }

 		b12Target OBJECT-TYPE
			SYNTAX DisplayString
			MAX-ACCESS not-accessible
			STATUS current
			DESCRIPTION
				"sensor Name"
			::= { blade12SensorTargetEntry 1 }
		
 		b12Current OBJECT-TYPE
			SYNTAX DisplayString
			MAX-ACCESS read-only
			STATUS current
			DESCRIPTION
				"Display the current value of a sensor."
			::= { blade12SensorTargetEntry 2 }
		
 		b12ThresholdsAll OBJECT-TYPE
			SYNTAX DisplayString
			MAX-ACCESS read-only
			STATUS current
			DESCRIPTION
				"All thresholds of a sensor"
			::= { blade12SensorTargetEntry 3 }
		
 		b12UpperCritical OBJECT-TYPE
			SYNTAX DisplayString
			MAX-ACCESS read-write
			STATUS current
			DESCRIPTION
				"Upper critical thresholds"
			::= { blade12SensorTargetEntry 4 }
		
 		b12UpperNonCritical OBJECT-TYPE
			SYNTAX DisplayString
			MAX-ACCESS read-write
			STATUS current
			DESCRIPTION
				"Upper non-critical thresholds"
			::= { blade12SensorTargetEntry 5 }
		
 		b12UpperNonRecoverable OBJECT-TYPE
			SYNTAX DisplayString
			MAX-ACCESS read-write
			STATUS current
			DESCRIPTION
				"Upper non-recoverable thresholds"
			::= { blade12SensorTargetEntry 6 }
		
 		b12LowerNonCritical OBJECT-TYPE
			SYNTAX DisplayString
			MAX-ACCESS read-write
			STATUS current
			DESCRIPTION
				"Lower non-critical thresholds"
			::= { blade12SensorTargetEntry 7 }
		
 		b12LowerCritical OBJECT-TYPE
			SYNTAX DisplayString
			MAX-ACCESS read-write
			STATUS current
			DESCRIPTION
				"Lower critical thresholds"
			::= { blade12SensorTargetEntry 8 }
		
 		b12LowerNonRecoverable OBJECT-TYPE
			SYNTAX DisplayString
			MAX-ACCESS read-write
			STATUS current
			DESCRIPTION
				"Lower non-recoverable thresholds"
			::= { blade12SensorTargetEntry 9 }
		
 		b12SensorHealth OBJECT-TYPE
			SYNTAX INTEGER
				{
				ok(0),
				minor(1),
				major(2),
				critical(3)
				}
			MAX-ACCESS read-only
			STATUS current
			DESCRIPTION
				"b12Health information about a particular b12Location. 
				This will be one of the following:
				(0-ok, 1-minor, 2-major, 3-critical)"
			::= { blade12SensorTargetEntry 10 }
		
 		b12SensorHealthEvents OBJECT-TYPE
			SYNTAX DisplayString
			MAX-ACCESS read-only
			STATUS current
			DESCRIPTION
				"Events that contribute to the b12Health of the b12Location.  
				This is a list of events currently happening on the 
				b12Location."
			::= { blade12SensorTargetEntry 11 }
		
		
 		b12NegativeHysteresis OBJECT-TYPE
			SYNTAX DisplayString
			MAX-ACCESS read-write
			STATUS current
			DESCRIPTION
				"Get/Set the negativeHysteresis value"
			::= { blade12SensorTargetEntry 16 }
		
 		b12PositiveHysteresis OBJECT-TYPE
			SYNTAX DisplayString
			MAX-ACCESS read-write
			STATUS current
			DESCRIPTION
				"Get/Set the positiveHysteresis value."
			::= { blade12SensorTargetEntry 17 }
		
 		b12SensorType OBJECT-TYPE
			SYNTAX DisplayString
			MAX-ACCESS read-only
			STATUS current
			DESCRIPTION
				"Get the type of the sensor."
			::= { blade12SensorTargetEntry 18 }
		
 		b12SensorFRUInfo OBJECT-TYPE
			SYNTAX DisplayString
			MAX-ACCESS read-only
			STATUS current
			DESCRIPTION
				"Get the fruinfo of the sensor."
			::= { blade12SensorTargetEntry 19 }
		
 		blade12FruTable OBJECT-TYPE
			SYNTAX SEQUENCE OF Blade12FruEntry
			MAX-ACCESS not-accessible
			STATUS current
			DESCRIPTION
				"A table containing the list of FRU information."
			::= { blade12 2002 }
		
 		blade12FruEntry OBJECT-TYPE
			SYNTAX Blade12FruEntry
			MAX-ACCESS not-accessible
			STATUS current
			DESCRIPTION
				"Information about a particular current FRU."
			INDEX { b12fruNumber }
			::= { blade12FruTable 1 }
		
		Blade12FruEntry ::=
			SEQUENCE { 
				b12fruNumber
					INTEGER,
				b12FruHotSwapState
					DisplayString,
				b12FruLedProperties
					DisplayString,
				b12FRUControl
					INTEGER,
				b12FRULabel
					DisplayString,
				b12ResetReason
					DisplayString
			 }

 		b12fruNumber OBJECT-TYPE
			SYNTAX INTEGER
			MAX-ACCESS not-accessible
			STATUS current
			DESCRIPTION
				" "
			::= { blade12FruEntry 1 }
		
 		b12FruHotSwapState OBJECT-TYPE
			SYNTAX DisplayString
			MAX-ACCESS read-only
			STATUS current
			DESCRIPTION
				"Retrieve the hot swap state of the FRU from the 
				internally known hot swap states of blade12."
			::= { blade12FruEntry 3 }
		
 		b12FruLedProperties OBJECT-TYPE
			SYNTAX DisplayString
			MAX-ACCESS read-only
			STATUS current
			DESCRIPTION
				"Retrieves the LED support information from a FRU. Returns a comma separated
				list of LEDS and the number of FRU supported user LEDs."
			::= { blade12FruEntry 4 }

		

		b12FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade12FruEntry 9 }
		
 		b12FRULabel OBJECT-TYPE
			SYNTAX DisplayString
			MAX-ACCESS read-only
			STATUS current
			DESCRIPTION
				"Get fru label of blade12."
			::= { blade12FruEntry 10 }
		
 		b12ResetReason OBJECT-TYPE
			SYNTAX DisplayString
			MAX-ACCESS read-only
			STATUS current
			DESCRIPTION
				"Delete fru label of smm."
			::= { blade12FruEntry 11 }
		
 		blade12FruLedTable OBJECT-TYPE
			SYNTAX SEQUENCE OF Blade12FruLedEntry
			MAX-ACCESS not-accessible
			STATUS current
			DESCRIPTION
				"A table containing the list of led information."
			::= { blade12 2003 }
		
 		blade12FruLedEntry OBJECT-TYPE
			SYNTAX Blade12FruLedEntry
			MAX-ACCESS not-accessible
			STATUS current
			DESCRIPTION
				"Information about a particular current led."
			INDEX { b12FruID, b12FruLed }
			::= { blade12FruLedTable 1 }
		
		Blade12FruLedEntry ::=
			SEQUENCE { 
				b12FruID
					INTEGER,
				b12FruLed
					DisplayString,
				b12FruLedColorProps
					DisplayString,
				b12FruLedState
					DisplayString
			 }

 		b12FruID OBJECT-TYPE
			SYNTAX INTEGER
			MAX-ACCESS not-accessible
			STATUS current
			DESCRIPTION
				" "
			::= { blade12FruLedEntry 1 }
		
 		b12FruLed OBJECT-TYPE
			SYNTAX DisplayString
			MAX-ACCESS not-accessible
			STATUS current
			DESCRIPTION
				" "
			::= { blade12FruLedEntry 2 }
		
 		b12FruLedColorProps OBJECT-TYPE
			SYNTAX DisplayString
			MAX-ACCESS read-only
			STATUS current
			DESCRIPTION
				"Finds out what colors are supported by the LED"
			::= { blade12FruLedEntry 3 }
		
 		b12FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade12FruLedEntry 4 }
		
 		blade12FruDescriptionTable OBJECT-TYPE
			SYNTAX SEQUENCE OF Blade12FruDescriptionEntry
			MAX-ACCESS not-accessible
			STATUS current
			DESCRIPTION
				"A table containing the list of blade12 FRU information."
			::= { blade12 2004 }
		
 		blade12FruDescriptionEntry OBJECT-TYPE
			SYNTAX Blade12FruDescriptionEntry
			MAX-ACCESS not-accessible
			STATUS current
			DESCRIPTION
				"Information about a particular current FRU."
			INDEX { b12fruNum }
			::= { blade12FruDescriptionTable 1 }
		
		Blade12FruDescriptionEntry ::=
			SEQUENCE { 
				b12fruNum
					INTEGER,
				b12fruBoardDescription
					DisplayString,
				b12fruBoardManufacturer
					DisplayString,
				b12fruBoardPartNumber
					DisplayString,
				b12fruBoardSerialNumber
					DisplayString,
				b12fruBoardManufactureDate
					DisplayString,
				b12fruProductDescription
					DisplayString,
				b12fruProductManufacturer
					DisplayString,
				b12fruProductPartNumber
					DisplayString,
				b12fruProductSerialNumber
					DisplayString,
				b12fruProductRevision
					DisplayString,
				b12fruAll
					DisplayString
			 }

 		b12fruNum OBJECT-TYPE
			SYNTAX INTEGER
			MAX-ACCESS not-accessible
			STATUS current
			DESCRIPTION
				"blade12 FRU's INDEX"
			::= { blade12FruDescriptionEntry 1 }
		
 		b12fruBoardDescription OBJECT-TYPE
			SYNTAX DisplayString
			MAX-ACCESS read-only
			STATUS current
			DESCRIPTION
				"Used to read the Board Description from the blade12 fru."
			::= { blade12FruDescriptionEntry 2 }
		
 		b12fruBoardManufacturer OBJECT-TYPE
			SYNTAX DisplayString
			MAX-ACCESS read-only
			STATUS current
			DESCRIPTION
				"Used to read the Board Manufacturer from the bladef12 fru."
			::= { blade12FruDescriptionEntry 3 }
		
 		b12fruBoardPartNumber OBJECT-TYPE
			SYNTAX DisplayString
			MAX-ACCESS read-only
			STATUS current
			DESCRIPTION
				"Used to read the Board Part Number from the blade12 fru."
			::= { blade12FruDescriptionEntry 4 }
		
 		b12fruBoardSerialNumber OBJECT-TYPE
			SYNTAX DisplayString
			MAX-ACCESS read-only
			STATUS current
			DESCRIPTION
				"Used to read the Board Serial Number from the blade12 fru."
			::= { blade12FruDescriptionEntry 5 }
		
 		b12fruBoardManufactureDate OBJECT-TYPE
			SYNTAX DisplayString
			MAX-ACCESS read-only
			STATUS current
			DESCRIPTION
				"Used to read the Board Manufacture Date from the blade12 fru."
			::= { blade12FruDescriptionEntry 6 }
		
 		b12fruProductDescription OBJECT-TYPE
			SYNTAX DisplayString
			MAX-ACCESS read-only
			STATUS current
			DESCRIPTION
				"Used to read the Product Description from the blade12 fru."
			::= { blade12FruDescriptionEntry 7 }
		
 		b12fruProductManufacturer OBJECT-TYPE
			SYNTAX DisplayString
			MAX-ACCESS read-only
			STATUS current
			DESCRIPTION
				"Used to read the Product Manufacturer from the blade12 fru."
			::= { blade12FruDescriptionEntry 8 }
		
 		b12fruProductPartNumber OBJECT-TYPE
			SYNTAX DisplayString
			MAX-ACCESS read-only
			STATUS current
			DESCRIPTION
				"Used to read the Product Part Number from the blade12 fru."
			::= { blade12FruDescriptionEntry 9 }
		
 		b12fruProductSerialNumber OBJECT-TYPE
			SYNTAX DisplayString
			MAX-ACCESS read-only
			STATUS current
			DESCRIPTION
				"Used to read the Product Serial Number from the blade12 fru."
			::= { blade12FruDescriptionEntry 10 }
		
 		b12fruProductRevision OBJECT-TYPE
			SYNTAX DisplayString
			MAX-ACCESS read-only
			STATUS current
			DESCRIPTION
				"Used to read the Product Revision from the blade12 fru."
			::= { blade12FruDescriptionEntry 13 }
		
 		b12fruAll OBJECT-TYPE
			SYNTAX DisplayString
			MAX-ACCESS read-only
			STATUS current
			DESCRIPTION
				"Used to read the fru info all."
			::= { blade12FruDescriptionEntry 14 }
		
		blade12CPUTable OBJECT-TYPE
			SYNTAX SEQUENCE OF Blade12CPUEntry
			MAX-ACCESS not-accessible
			STATUS current
			DESCRIPTION
				"A table containing the list of Blade1 FRU information."
			::= { blade12 2006 }
		
		blade12CPUEntry OBJECT-TYPE
			SYNTAX Blade12CPUEntry
			MAX-ACCESS not-accessible
			STATUS current
			DESCRIPTION
				"Information about a particular current FRU."
			INDEX { b12CPUIndex }
			::= { blade12CPUTable 1 }
		
		Blade12CPUEntry ::=
			SEQUENCE { 
				b12CPUIndex
					INTEGER,
				b12CPUMark
					DisplayString,
				b12CPUInfo
					DisplayString,
				b12CPUPresent
					INTEGER,
				b12CPUHealth
					INTEGER,
				b12CPULocation
					DisplayString
			 }

		b12CPUIndex OBJECT-TYPE
			SYNTAX INTEGER
			MAX-ACCESS not-accessible
			STATUS current
			DESCRIPTION
				"CPU INDEX"
			::= { blade12CPUEntry 1 }
		
		b12CPUMark OBJECT-TYPE
			SYNTAX DisplayString
			MAX-ACCESS read-only
			STATUS current
			DESCRIPTION
				"Get the CPU silk-screen."
			::= { blade12CPUEntry 2 }
		
		b12CPUInfo OBJECT-TYPE
			SYNTAX DisplayString
			MAX-ACCESS read-only
			STATUS current
			DESCRIPTION
				"Get the CPU description of vendor, type and frequency."
			::= { blade12CPUEntry 3 }
		
		b12CPUPresent OBJECT-TYPE
			SYNTAX INTEGER
			MAX-ACCESS read-only
			STATUS current
			DESCRIPTION
				"Get the CPU presence status."
			::= { blade12CPUEntry 4 }
		
		b12CPUHealth OBJECT-TYPE
			SYNTAX INTEGER
			MAX-ACCESS read-only
			STATUS current
			DESCRIPTION
				"Get the CPU health status."
			::= { blade12CPUEntry 5 }
		
		b12CPULocation OBJECT-TYPE
			SYNTAX DisplayString
			MAX-ACCESS read-only
			STATUS current
			DESCRIPTION
				"Get the CPU location."
			::= { blade12CPUEntry 6 }
		
		blade12MemoryTable OBJECT-TYPE
			SYNTAX SEQUENCE OF Blade12MemoryEntry
			MAX-ACCESS not-accessible
			STATUS current
			DESCRIPTION
				"A table containing the list of Blade1 FRU information."
			::= { blade12 2007 }
		
		blade12MemoryEntry OBJECT-TYPE
			SYNTAX Blade12MemoryEntry
			MAX-ACCESS not-accessible
			STATUS current
			DESCRIPTION
				"Information about a particular current FRU."
			INDEX { b12MEMIndex }
			::= { blade12MemoryTable 1 }
		
		Blade12MemoryEntry ::=
			SEQUENCE { 
				b12MEMIndex
					INTEGER,
				b12MEMMark
					DisplayString,
				b12MEMInfo
					DisplayString,
				b12MEMPresent
					INTEGER,
				b12MEMHealth
					INTEGER,
				b12MEMLocation
					DisplayString
			 }

		b12MEMIndex OBJECT-TYPE
			SYNTAX INTEGER
			MAX-ACCESS not-accessible
			STATUS current
			DESCRIPTION
				"MEMORY INDEX"
			::= { blade12MemoryEntry 1 }
		
		b12MEMMark OBJECT-TYPE
			SYNTAX DisplayString
			MAX-ACCESS read-only
			STATUS current
			DESCRIPTION
				"Get the memory silk-screen."
			::= { blade12MemoryEntry 2 }
		
		b12MEMInfo OBJECT-TYPE
			SYNTAX DisplayString
			MAX-ACCESS read-only
			STATUS current
			DESCRIPTION
				"Get the memory description of vendor, frequency and capacity."
			::= { blade12MemoryEntry 3 }
		
		b12MEMPresent OBJECT-TYPE
			SYNTAX INTEGER
			MAX-ACCESS read-only
			STATUS current
			DESCRIPTION
				"Get the memory presence status."
			::= { blade12MemoryEntry 4 }
		
		b12MEMHealth OBJECT-TYPE
			SYNTAX INTEGER
			MAX-ACCESS read-only
			STATUS current
			DESCRIPTION
				"Get the memory health status."
			::= { blade12MemoryEntry 5 }
		
		b12MEMLocation OBJECT-TYPE
			SYNTAX DisplayString
			MAX-ACCESS read-only
			STATUS current
			DESCRIPTION
				"Get the memory location."
			::= { blade12MemoryEntry 6 }
		
		blade12MezzTable OBJECT-TYPE
			SYNTAX SEQUENCE OF Blade12MezzEntry
			MAX-ACCESS not-accessible
			STATUS current
			DESCRIPTION
				"A table containing the list of Blade1 FRU information."
			::= { blade12 2008 }
		
		blade12MezzEntry OBJECT-TYPE
			SYNTAX Blade12MezzEntry
			MAX-ACCESS not-accessible
			STATUS current
			DESCRIPTION
				"Information about a particular current FRU."
			INDEX { b12MezzIndex }
			::= { blade12MezzTable 1 }
		
		Blade12MezzEntry ::=
			SEQUENCE { 
				b12MezzIndex
					INTEGER,
				b12MezzMark
					DisplayString,
				b12MezzInfo
					DisplayString,
				b12MezzPresent
					INTEGER,
				b12MezzHealth
					INTEGER,
				b12MezzLocation
					DisplayString,
				b12MezzMac
					DisplayString
			 }

		b12MezzIndex OBJECT-TYPE
			SYNTAX INTEGER
			MAX-ACCESS not-accessible
			STATUS current
			DESCRIPTION
				"MEZZ INDEX"
			::= { blade12MezzEntry 1 }
		
		b12MezzMark OBJECT-TYPE
			SYNTAX DisplayString
			MAX-ACCESS read-only
			STATUS current
			DESCRIPTION
				"Get the MEZZ silk-screen."
			::= { blade12MezzEntry 2 }
		
		b12MezzInfo OBJECT-TYPE
			SYNTAX DisplayString
			MAX-ACCESS read-only
			STATUS current
			DESCRIPTION
				"Get the MEZZ description of type."
			::= { blade12MezzEntry 3 }
		
		b12MezzPresent OBJECT-TYPE
			SYNTAX INTEGER
			MAX-ACCESS read-only
			STATUS current
			DESCRIPTION
				"Get the MEZZ presence status."
			::= { blade12MezzEntry 4 }
		
		b12MezzHealth OBJECT-TYPE
			SYNTAX INTEGER
			MAX-ACCESS read-only
			STATUS current
			DESCRIPTION
				"Get the MEZZ health status."
			::= { blade12MezzEntry 5 }
		
		b12MezzLocation OBJECT-TYPE
			SYNTAX DisplayString
			MAX-ACCESS read-only
			STATUS current
			DESCRIPTION
				"Get the MEZZ location."
			::= { blade12MezzEntry 6 }
		
		b12MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade12MezzEntry 7 }
		
		blade12DiskTable OBJECT-TYPE
			SYNTAX SEQUENCE OF Blade12DiskEntry
			MAX-ACCESS not-accessible
			STATUS current
			DESCRIPTION
				"A table containing the list of Blade1 FRU information."
			::= { blade12 2009 }
		
		blade12DiskEntry OBJECT-TYPE
			SYNTAX Blade12DiskEntry
			MAX-ACCESS not-accessible
			STATUS current
			DESCRIPTION
				"Information about a particular current FRU."
			INDEX { b12DiskIndex }
			::= { blade12DiskTable 1 }
		
		Blade12DiskEntry ::=
			SEQUENCE { 
				b12DiskIndex
					INTEGER,
				b12DiskMark
					DisplayString,
				b12DiskInfo
					DisplayString,
				b12DiskPresent
					INTEGER,
				b12DiskHealth
					INTEGER,
				b12DiskLocation
					DisplayString
			 }

		b12DiskIndex OBJECT-TYPE
			SYNTAX INTEGER
			MAX-ACCESS not-accessible
			STATUS current
			DESCRIPTION
				"DISK INDEX"
			::= { blade12DiskEntry 1 }
		
		b12DiskMark OBJECT-TYPE
			SYNTAX DisplayString
			MAX-ACCESS read-only
			STATUS current
			DESCRIPTION
				"Get the disk silk-screen."
			::= { blade12DiskEntry 2 }
		
		b12DiskInfo OBJECT-TYPE
			SYNTAX DisplayString
			MAX-ACCESS read-only
			STATUS current
			DESCRIPTION
				"Get the disk description of vendor, capacity and speed."
			::= { blade12DiskEntry 3 }
		
		b12DiskPresent OBJECT-TYPE
			SYNTAX INTEGER
			MAX-ACCESS read-only
			STATUS current
			DESCRIPTION
				"Get the disk presence status."
			::= { blade12DiskEntry 4 }
		
		b12DiskHealth OBJECT-TYPE
			SYNTAX INTEGER
			MAX-ACCESS read-only
			STATUS current
			DESCRIPTION
				"Get the disk health status."
			::= { blade12DiskEntry 5 }
		
		b12DiskLocation OBJECT-TYPE
			SYNTAX DisplayString
			MAX-ACCESS read-only
			STATUS current
			DESCRIPTION
				"Get the disk location."
			::= { blade12DiskEntry 6 }
		
		blade12SecretKvmVmmTable OBJECT-TYPE
			SYNTAX SEQUENCE OF Blade12SecretKvmVmmEntry
			MAX-ACCESS not-accessible
			STATUS current
			DESCRIPTION
				"A table containing the list of Blade12 KVM&VMM secret information."
			::= { blade12 2010 }

		blade12SecretKvmVmmEntry OBJECT-TYPE
			SYNTAX Blade12SecretKvmVmmEntry
			MAX-ACCESS not-accessible
			STATUS current
			DESCRIPTION
				"Information about a particular current KVM&VMM."
			INDEX { b12SecretKvmVmmIndex }
			::= { blade12SecretKvmVmmTable 1 }
		Blade12SecretKvmVmmEntry ::=
			SEQUENCE { 
				b12SecretKvmVmmIndex
					INTEGER,
				b12SecretKvmState
					INTEGER,
				b12SecretVmmState
					INTEGER,
				b12MMSecretVmmKey
					DisplayString,
				b12SecretVmmKey
					DisplayString
			 }
		b12SecretKvmVmmIndex OBJECT-TYPE
			SYNTAX INTEGER
			MAX-ACCESS not-accessible
			STATUS current
			DESCRIPTION
				"KVM&VMM INDEX."
			::= { blade12SecretKvmVmmEntry 1 }
		b12SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade12SecretKvmVmmEntry 2 }
		b12SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade12SecretKvmVmmEntry 3 }
		b12MMSecretVmmKey OBJECT-TYPE
			SYNTAX DisplayString
			MAX-ACCESS read-only
			STATUS current
			DESCRIPTION
				"Get the MM secret VMM key."
			::= { blade12SecretKvmVmmEntry 4 }
		b12SecretVmmKey OBJECT-TYPE
			SYNTAX DisplayString
			MAX-ACCESS read-write
			STATUS current
			DESCRIPTION
				"Set the secret VMM key."
			::= { blade12SecretKvmVmmEntry 5 }
		blade13 OBJECT IDENTIFIER ::= { blades 13 }

		
 		b13DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade13 4 }
		
 		b13PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade13 5 }
		
 		b13Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade13 6 }

		
 		b13Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b13Health information about a particular b13Location. 
				This will be one of the following:
				(0-ok, 1-minor, 2-major, 3-majorandminor,4-critical,5-criticalandminor,6-criticalandmajor,7-criticalandmajorandminor)"
			::= { blade13 8 }
		
 		b13HealthEvents OBJECT-TYPE
			SYNTAX DisplayString
			MAX-ACCESS read-only
			STATUS current
			DESCRIPTION
				"Events that contribute to the b13Health of the b13Location.  
				This is a list of events currently happening on the 
				b13Location."
			::= { blade13 9 }
		
 		b13ClearSEL OBJECT-TYPE
			SYNTAX INTEGER { clear(1) }
			MAX-ACCESS read-write
			STATUS current
			DESCRIPTION
				"Clean the BMC's SEL on the board."
			::= { blade13 12 }
		
 		b13ExDiskBoardPresence OBJECT-TYPE
			SYNTAX INTEGER
				{
				not-present(0),
				present(1)
				}
			MAX-ACCESS read-only
			STATUS current
			DESCRIPTION
				"Used to find out if the extended disk board is present.
				0 - not present
				1 - present"
			::= { blade13 14 }
		
 		b13BladeVersion OBJECT-TYPE
			SYNTAX DisplayString
			MAX-ACCESS read-only
			STATUS current
			DESCRIPTION
				"display the Version of board13."
			::= { blade13 20 }
		
 		b13MACAddress OBJECT-TYPE
			SYNTAX DisplayString
			MAX-ACCESS read-only
			STATUS current
			DESCRIPTION
				"display the MACAddress of board13."
			::= { blade13 21 }
		
		
 		b13Safepwofftime OBJECT-TYPE
			SYNTAX INTEGER
			MAX-ACCESS read-write
			STATUS current
			DESCRIPTION
				"the safe poweroff time.
				"
			::= { blade13 26 }
		
 		b13BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade13 32 }
		
 		b13Systeminfo OBJECT-TYPE
			SYNTAX DisplayString
			MAX-ACCESS read-write
			STATUS current
			DESCRIPTION
				"display the system information of board13."
			::= { blade13 36 }

		
 		b13SystemProperties OBJECT-TYPE
			SYNTAX DisplayString
			MAX-ACCESS read-only
			STATUS current
			DESCRIPTION
				"Get the power of blade1."
			::= { blade13 39 }
		
 		b13BiosCfg OBJECT-TYPE
			SYNTAX DisplayString
			MAX-ACCESS read-write
			STATUS current
			DESCRIPTION
				"Get the power of blade1."
			::= { blade13 40 }
		
 		b13WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade13 41 }
		
 		b13RealTimePower OBJECT-TYPE
			SYNTAX INTEGER
			MAX-ACCESS read-only
			STATUS current
			DESCRIPTION
				" "
			::= { blade13 43 }
		
 		b13PowerCapping OBJECT-TYPE
			SYNTAX DisplayString
			MAX-ACCESS read-write
			STATUS current
			DESCRIPTION
				" "
			::= { blade13 44 }
		
 		b13Powerreference OBJECT-TYPE
			SYNTAX INTEGER
			MAX-ACCESS read-only
			STATUS current
			DESCRIPTION
				" "
			::= { blade13 45 }
		
 		b13ClearBiosConfig OBJECT-TYPE
			SYNTAX INTEGER
			MAX-ACCESS read-write
			STATUS current
			DESCRIPTION
				" "
			::= { blade13 46 }
		
 		b13BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade13 47 }
		
 		b13BmcUserAdd OBJECT-TYPE
			SYNTAX DisplayString
			MAX-ACCESS read-write
			STATUS current
			DESCRIPTION
				"Used to Add the BMC User
				settable format:
				username,passwd"
			::= { blade13 48 }
		
 		b13BmcUserDel OBJECT-TYPE
			SYNTAX DisplayString
			MAX-ACCESS read-write
			STATUS current
			DESCRIPTION
				"Used to Del the BMC User
				settable format:
				username"
			::= { blade13 49 }
		
 		b13BmcUserPasswd OBJECT-TYPE
			SYNTAX DisplayString
			MAX-ACCESS read-write
			STATUS current
			DESCRIPTION
				"Used to Change the BMC User Passwd
				settable format:
				username,passwd"
			::= { blade13 50 }
		
 		b13BmcUserpropertychg OBJECT-TYPE
			SYNTAX DisplayString
			MAX-ACCESS read-write
			STATUS current
			DESCRIPTION
				"Used to Change the BMC User Property
				settable format:
				username,property"
			::= { blade13 51 }
		
 		b13BmcGateway OBJECT-TYPE
			SYNTAX DisplayString
			MAX-ACCESS read-write
			STATUS current
			DESCRIPTION
				"Read or set the gateway."
			::= { blade13 52 }
		
 		b13SlotBitmap OBJECT-TYPE
			SYNTAX INTEGER
			MAX-ACCESS read-only
			STATUS current
			DESCRIPTION
				" "
			::= { blade13 55 }
		
		b13systemGuid OBJECT-TYPE
			SYNTAX DisplayString
			MAX-ACCESS read-only
			STATUS current
			DESCRIPTION
				" "
			::= { blade13 56 }
		
		b13ProductName OBJECT-TYPE
			SYNTAX DisplayString
			MAX-ACCESS read-only
			STATUS current
			DESCRIPTION
				"display the Version of board13."
			::= { blade13 57 }
		
		b13BundleVersion OBJECT-TYPE
			SYNTAX DisplayString
			MAX-ACCESS read-write
			STATUS current
			DESCRIPTION
				"Get or set the board13 bundle version."
			::= { blade13 58 }

 		blade13SensorTargetTable OBJECT-TYPE
			SYNTAX SEQUENCE OF Blade13SensorTargetEntry
			MAX-ACCESS not-accessible
			STATUS current
			DESCRIPTION
				"A table containing the list of sensor information."
			::= { blade13 2001 }
		
 		blade13SensorTargetEntry OBJECT-TYPE
			SYNTAX Blade13SensorTargetEntry
			MAX-ACCESS not-accessible
			STATUS current
			DESCRIPTION
				"Information about a particular current sensor."
			INDEX { b13Target }
			::= { blade13SensorTargetTable 1 }
		
		Blade13SensorTargetEntry ::=
			SEQUENCE { 
				b13Target
					DisplayString,
				b13Current
					DisplayString,
				b13ThresholdsAll
					DisplayString,
				b13UpperCritical
					DisplayString,
				b13UpperNonCritical
					DisplayString,
				b13UpperNonRecoverable
					DisplayString,
				b13LowerNonCritical
					DisplayString,
				b13LowerCritical
					DisplayString,
				b13LowerNonRecoverable
					DisplayString,
				b13SensorHealth
					INTEGER,
				b13SensorHealthEvents
					DisplayString,
				b13NegativeHysteresis
					DisplayString,
				b13PositiveHysteresis
					DisplayString,
				b13SensorType
					DisplayString,
				b13SensorFRUInfo
					DisplayString
			 }

 		b13Target OBJECT-TYPE
			SYNTAX DisplayString
			MAX-ACCESS not-accessible
			STATUS current
			DESCRIPTION
				"sensor Name"
			::= { blade13SensorTargetEntry 1 }
		
 		b13Current OBJECT-TYPE
			SYNTAX DisplayString
			MAX-ACCESS read-only
			STATUS current
			DESCRIPTION
				"Display the current value of a sensor."
			::= { blade13SensorTargetEntry 2 }
		
 		b13ThresholdsAll OBJECT-TYPE
			SYNTAX DisplayString
			MAX-ACCESS read-only
			STATUS current
			DESCRIPTION
				"All thresholds of a sensor"
			::= { blade13SensorTargetEntry 3 }
		
 		b13UpperCritical OBJECT-TYPE
			SYNTAX DisplayString
			MAX-ACCESS read-write
			STATUS current
			DESCRIPTION
				"Upper critical thresholds"
			::= { blade13SensorTargetEntry 4 }
		
 		b13UpperNonCritical OBJECT-TYPE
			SYNTAX DisplayString
			MAX-ACCESS read-write
			STATUS current
			DESCRIPTION
				"Upper non-critical thresholds"
			::= { blade13SensorTargetEntry 5 }
		
 		b13UpperNonRecoverable OBJECT-TYPE
			SYNTAX DisplayString
			MAX-ACCESS read-write
			STATUS current
			DESCRIPTION
				"Upper non-recoverable thresholds"
			::= { blade13SensorTargetEntry 6 }
		
 		b13LowerNonCritical OBJECT-TYPE
			SYNTAX DisplayString
			MAX-ACCESS read-write
			STATUS current
			DESCRIPTION
				"Lower non-critical thresholds"
			::= { blade13SensorTargetEntry 7 }
		
 		b13LowerCritical OBJECT-TYPE
			SYNTAX DisplayString
			MAX-ACCESS read-write
			STATUS current
			DESCRIPTION
				"Lower critical thresholds"
			::= { blade13SensorTargetEntry 8 }
		
 		b13LowerNonRecoverable OBJECT-TYPE
			SYNTAX DisplayString
			MAX-ACCESS read-write
			STATUS current
			DESCRIPTION
				"Lower non-recoverable thresholds"
			::= { blade13SensorTargetEntry 9 }
		
 		b13SensorHealth OBJECT-TYPE
			SYNTAX INTEGER
				{
				ok(0),
				minor(1),
				major(2),
				critical(3)
				}
			MAX-ACCESS read-only
			STATUS current
			DESCRIPTION
				"b13Health information about a particular b13Location. 
				This will be one of the following:
				(0-ok, 1-minor, 2-major, 3-critical)"
			::= { blade13SensorTargetEntry 10 }
		
 		b13SensorHealthEvents OBJECT-TYPE
			SYNTAX DisplayString
			MAX-ACCESS read-only
			STATUS current
			DESCRIPTION
				"Events that contribute to the b13Health of the b13Location.  
				This is a list of events currently happening on the 
				b13Location."
			::= { blade13SensorTargetEntry 11 }
		
		
 		b13NegativeHysteresis OBJECT-TYPE
			SYNTAX DisplayString
			MAX-ACCESS read-write
			STATUS current
			DESCRIPTION
				"Get/Set the negativeHysteresis value"
			::= { blade13SensorTargetEntry 16 }
		
 		b13PositiveHysteresis OBJECT-TYPE
			SYNTAX DisplayString
			MAX-ACCESS read-write
			STATUS current
			DESCRIPTION
				"Get/Set the positiveHysteresis value."
			::= { blade13SensorTargetEntry 17 }
		
 		b13SensorType OBJECT-TYPE
			SYNTAX DisplayString
			MAX-ACCESS read-only
			STATUS current
			DESCRIPTION
				"Get the type of the sensor."
			::= { blade13SensorTargetEntry 18 }
		
 		b13SensorFRUInfo OBJECT-TYPE
			SYNTAX DisplayString
			MAX-ACCESS read-only
			STATUS current
			DESCRIPTION
				"Get the fruinfo of the sensor."
			::= { blade13SensorTargetEntry 19 }
		
 		blade13FruTable OBJECT-TYPE
			SYNTAX SEQUENCE OF Blade13FruEntry
			MAX-ACCESS not-accessible
			STATUS current
			DESCRIPTION
				"A table containing the list of FRU information."
			::= { blade13 2002 }
		
 		blade13FruEntry OBJECT-TYPE
			SYNTAX Blade13FruEntry
			MAX-ACCESS not-accessible
			STATUS current
			DESCRIPTION
				"Information about a particular current FRU."
			INDEX { b13fruNumber }
			::= { blade13FruTable 1 }
		
		Blade13FruEntry ::=
			SEQUENCE { 
				b13fruNumber
					INTEGER,
				b13FruHotSwapState
					DisplayString,
				b13FruLedProperties
					DisplayString,
				b13FRUControl
					INTEGER,
				b13FRULabel
					DisplayString,
				b13ResetReason
					DisplayString
			 }

 		b13fruNumber OBJECT-TYPE
			SYNTAX INTEGER
			MAX-ACCESS not-accessible
			STATUS current
			DESCRIPTION
				" "
			::= { blade13FruEntry 1 }
		
 		b13FruHotSwapState OBJECT-TYPE
			SYNTAX DisplayString
			MAX-ACCESS read-only
			STATUS current
			DESCRIPTION
				"Retrieve the hot swap state of the FRU from the 
				internally known hot swap states of blade13."
			::= { blade13FruEntry 3 }
		
 		b13FruLedProperties OBJECT-TYPE
			SYNTAX DisplayString
			MAX-ACCESS read-only
			STATUS current
			DESCRIPTION
				"Retrieves the LED support information from a FRU. Returns a comma separated
				list of LEDS and the number of FRU supported user LEDs."
			::= { blade13FruEntry 4 }

		

		b13FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade13FruEntry 9 }
		
 		b13FRULabel OBJECT-TYPE
			SYNTAX DisplayString
			MAX-ACCESS read-only
			STATUS current
			DESCRIPTION
				"Get fru label of blade13."
			::= { blade13FruEntry 10 }
		
 		b13ResetReason OBJECT-TYPE
			SYNTAX DisplayString
			MAX-ACCESS read-only
			STATUS current
			DESCRIPTION
				"Delete fru label of smm."
			::= { blade13FruEntry 11 }
		
 		blade13FruLedTable OBJECT-TYPE
			SYNTAX SEQUENCE OF Blade13FruLedEntry
			MAX-ACCESS not-accessible
			STATUS current
			DESCRIPTION
				"A table containing the list of led information."
			::= { blade13 2003 }
		
 		blade13FruLedEntry OBJECT-TYPE
			SYNTAX Blade13FruLedEntry
			MAX-ACCESS not-accessible
			STATUS current
			DESCRIPTION
				"Information about a particular current led."
			INDEX { b13FruID, b13FruLed }
			::= { blade13FruLedTable 1 }
		
		Blade13FruLedEntry ::=
			SEQUENCE { 
				b13FruID
					INTEGER,
				b13FruLed
					DisplayString,
				b13FruLedColorProps
					DisplayString,
				b13FruLedState
					DisplayString
			 }

 		b13FruID OBJECT-TYPE
			SYNTAX INTEGER
			MAX-ACCESS not-accessible
			STATUS current
			DESCRIPTION
				" "
			::= { blade13FruLedEntry 1 }
		
 		b13FruLed OBJECT-TYPE
			SYNTAX DisplayString
			MAX-ACCESS not-accessible
			STATUS current
			DESCRIPTION
				" "
			::= { blade13FruLedEntry 2 }
		
 		b13FruLedColorProps OBJECT-TYPE
			SYNTAX DisplayString
			MAX-ACCESS read-only
			STATUS current
			DESCRIPTION
				"Finds out what colors are supported by the LED"
			::= { blade13FruLedEntry 3 }
		
 		b13FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade13FruLedEntry 4 }
		
 		blade13FruDescriptionTable OBJECT-TYPE
			SYNTAX SEQUENCE OF Blade13FruDescriptionEntry
			MAX-ACCESS not-accessible
			STATUS current
			DESCRIPTION
				"A table containing the list of blade13 FRU information."
			::= { blade13 2004 }
		
 		blade13FruDescriptionEntry OBJECT-TYPE
			SYNTAX Blade13FruDescriptionEntry
			MAX-ACCESS not-accessible
			STATUS current
			DESCRIPTION
				"Information about a particular current FRU."
			INDEX { b13fruNum }
			::= { blade13FruDescriptionTable 1 }
		
		Blade13FruDescriptionEntry ::=
			SEQUENCE { 
				b13fruNum
					INTEGER,
				b13fruBoardDescription
					DisplayString,
				b13fruBoardManufacturer
					DisplayString,
				b13fruBoardPartNumber
					DisplayString,
				b13fruBoardSerialNumber
					DisplayString,
				b13fruBoardManufactureDate
					DisplayString,
				b13fruProductDescription
					DisplayString,
				b13fruProductManufacturer
					DisplayString,
				b13fruProductPartNumber
					DisplayString,
				b13fruProductSerialNumber
					DisplayString,
				b13fruProductRevision
					DisplayString,
				b13fruAll
					DisplayString
			 }

 		b13fruNum OBJECT-TYPE
			SYNTAX INTEGER
			MAX-ACCESS not-accessible
			STATUS current
			DESCRIPTION
				"blade13 FRU's INDEX"
			::= { blade13FruDescriptionEntry 1 }
		
 		b13fruBoardDescription OBJECT-TYPE
			SYNTAX DisplayString
			MAX-ACCESS read-only
			STATUS current
			DESCRIPTION
				"Used to read the Board Description from the blade13 fru."
			::= { blade13FruDescriptionEntry 2 }
		
 		b13fruBoardManufacturer OBJECT-TYPE
			SYNTAX DisplayString
			MAX-ACCESS read-only
			STATUS current
			DESCRIPTION
				"Used to read the Board Manufacturer from the bladef13 fru."
			::= { blade13FruDescriptionEntry 3 }
		
 		b13fruBoardPartNumber OBJECT-TYPE
			SYNTAX DisplayString
			MAX-ACCESS read-only
			STATUS current
			DESCRIPTION
				"Used to read the Board Part Number from the blade13 fru."
			::= { blade13FruDescriptionEntry 4 }
		
 		b13fruBoardSerialNumber OBJECT-TYPE
			SYNTAX DisplayString
			MAX-ACCESS read-only
			STATUS current
			DESCRIPTION
				"Used to read the Board Serial Number from the blade13 fru."
			::= { blade13FruDescriptionEntry 5 }
		
 		b13fruBoardManufactureDate OBJECT-TYPE
			SYNTAX DisplayString
			MAX-ACCESS read-only
			STATUS current
			DESCRIPTION
				"Used to read the Board Manufacture Date from the blade13 fru."
			::= { blade13FruDescriptionEntry 6 }
		
 		b13fruProductDescription OBJECT-TYPE
			SYNTAX DisplayString
			MAX-ACCESS read-only
			STATUS current
			DESCRIPTION
				"Used to read the Product Description from the blade13 fru."
			::= { blade13FruDescriptionEntry 7 }
		
 		b13fruProductManufacturer OBJECT-TYPE
			SYNTAX DisplayString
			MAX-ACCESS read-only
			STATUS current
			DESCRIPTION
				"Used to read the Product Manufacturer from the blade13 fru."
			::= { blade13FruDescriptionEntry 8 }
		
 		b13fruProductPartNumber OBJECT-TYPE
			SYNTAX DisplayString
			MAX-ACCESS read-only
			STATUS current
			DESCRIPTION
				"Used to read the Product Part Number from the blade13 fru."
			::= { blade13FruDescriptionEntry 9 }
		
 		b13fruProductSerialNumber OBJECT-TYPE
			SYNTAX DisplayString
			MAX-ACCESS read-only
			STATUS current
			DESCRIPTION
				"Used to read the Product Serial Number from the blade13 fru."
			::= { blade13FruDescriptionEntry 10 }
		
 		b13fruProductRevision OBJECT-TYPE
			SYNTAX DisplayString
			MAX-ACCESS read-only
			STATUS current
			DESCRIPTION
				"Used to read the Product Revision from the blade13 fru."
			::= { blade13FruDescriptionEntry 13 }
		
 		b13fruAll OBJECT-TYPE
			SYNTAX DisplayString
			MAX-ACCESS read-only
			STATUS current
			DESCRIPTION
				"Used to read the fru info all."
			::= { blade13FruDescriptionEntry 14 }
		
		blade13CPUTable OBJECT-TYPE
			SYNTAX SEQUENCE OF Blade13CPUEntry
			MAX-ACCESS not-accessible
			STATUS current
			DESCRIPTION
				"A table containing the list of Blade1 FRU information."
			::= { blade13 2006 }
		
		blade13CPUEntry OBJECT-TYPE
			SYNTAX Blade13CPUEntry
			MAX-ACCESS not-accessible
			STATUS current
			DESCRIPTION
				"Information about a particular current FRU."
			INDEX { b13CPUIndex }
			::= { blade13CPUTable 1 }
		
		Blade13CPUEntry ::=
			SEQUENCE { 
				b13CPUIndex
					INTEGER,
				b13CPUMark
					DisplayString,
				b13CPUInfo
					DisplayString,
				b13CPUPresent
					INTEGER,
				b13CPUHealth
					INTEGER,
				b13CPULocation
					DisplayString
			 }

		b13CPUIndex OBJECT-TYPE
			SYNTAX INTEGER
			MAX-ACCESS not-accessible
			STATUS current
			DESCRIPTION
				"CPU INDEX"
			::= { blade13CPUEntry 1 }
		
		b13CPUMark OBJECT-TYPE
			SYNTAX DisplayString
			MAX-ACCESS read-only
			STATUS current
			DESCRIPTION
				"Get the CPU silk-screen."
			::= { blade13CPUEntry 2 }
		
		b13CPUInfo OBJECT-TYPE
			SYNTAX DisplayString
			MAX-ACCESS read-only
			STATUS current
			DESCRIPTION
				"Get the CPU description of vendor, type and frequency."
			::= { blade13CPUEntry 3 }
		
		b13CPUPresent OBJECT-TYPE
			SYNTAX INTEGER
			MAX-ACCESS read-only
			STATUS current
			DESCRIPTION
				"Get the CPU presence status."
			::= { blade13CPUEntry 4 }
		
		b13CPUHealth OBJECT-TYPE
			SYNTAX INTEGER
			MAX-ACCESS read-only
			STATUS current
			DESCRIPTION
				"Get the CPU health status."
			::= { blade13CPUEntry 5 }
		
		b13CPULocation OBJECT-TYPE
			SYNTAX DisplayString
			MAX-ACCESS read-only
			STATUS current
			DESCRIPTION
				"Get the CPU location."
			::= { blade13CPUEntry 6 }
		
		blade13MemoryTable OBJECT-TYPE
			SYNTAX SEQUENCE OF Blade13MemoryEntry
			MAX-ACCESS not-accessible
			STATUS current
			DESCRIPTION
				"A table containing the list of Blade1 FRU information."
			::= { blade13 2007 }
		
		blade13MemoryEntry OBJECT-TYPE
			SYNTAX Blade13MemoryEntry
			MAX-ACCESS not-accessible
			STATUS current
			DESCRIPTION
				"Information about a particular current FRU."
			INDEX { b13MEMIndex }
			::= { blade13MemoryTable 1 }
		
		Blade13MemoryEntry ::=
			SEQUENCE { 
				b13MEMIndex
					INTEGER,
				b13MEMMark
					DisplayString,
				b13MEMInfo
					DisplayString,
				b13MEMPresent
					INTEGER,
				b13MEMHealth
					INTEGER,
				b13MEMLocation
					DisplayString
			 }

		b13MEMIndex OBJECT-TYPE
			SYNTAX INTEGER
			MAX-ACCESS not-accessible
			STATUS current
			DESCRIPTION
				"MEMORY INDEX"
			::= { blade13MemoryEntry 1 }
		
		b13MEMMark OBJECT-TYPE
			SYNTAX DisplayString
			MAX-ACCESS read-only
			STATUS current
			DESCRIPTION
				"Get the memory silk-screen."
			::= { blade13MemoryEntry 2 }
		
		b13MEMInfo OBJECT-TYPE
			SYNTAX DisplayString
			MAX-ACCESS read-only
			STATUS current
			DESCRIPTION
				"Get the memory description of vendor, frequency and capacity."
			::= { blade13MemoryEntry 3 }
		
		b13MEMPresent OBJECT-TYPE
			SYNTAX INTEGER
			MAX-ACCESS read-only
			STATUS current
			DESCRIPTION
				"Get the memory presence status."
			::= { blade13MemoryEntry 4 }
		
		b13MEMHealth OBJECT-TYPE
			SYNTAX INTEGER
			MAX-ACCESS read-only
			STATUS current
			DESCRIPTION
				"Get the memory health status."
			::= { blade13MemoryEntry 5 }
		
		b13MEMLocation OBJECT-TYPE
			SYNTAX DisplayString
			MAX-ACCESS read-only
			STATUS current
			DESCRIPTION
				"Get the memory location."
			::= { blade13MemoryEntry 6 }
		
		blade13MezzTable OBJECT-TYPE
			SYNTAX SEQUENCE OF Blade13MezzEntry
			MAX-ACCESS not-accessible
			STATUS current
			DESCRIPTION
				"A table containing the list of Blade1 FRU information."
			::= { blade13 2008 }
		
		blade13MezzEntry OBJECT-TYPE
			SYNTAX Blade13MezzEntry
			MAX-ACCESS not-accessible
			STATUS current
			DESCRIPTION
				"Information about a particular current FRU."
			INDEX { b13MezzIndex }
			::= { blade13MezzTable 1 }
		
		Blade13MezzEntry ::=
			SEQUENCE { 
				b13MezzIndex
					INTEGER,
				b13MezzMark
					DisplayString,
				b13MezzInfo
					DisplayString,
				b13MezzPresent
					INTEGER,
				b13MezzHealth
					INTEGER,
				b13MezzLocation
					DisplayString,
				b13MezzMac
					DisplayString
			 }

		b13MezzIndex OBJECT-TYPE
			SYNTAX INTEGER
			MAX-ACCESS not-accessible
			STATUS current
			DESCRIPTION
				"MEZZ INDEX"
			::= { blade13MezzEntry 1 }
		
		b13MezzMark OBJECT-TYPE
			SYNTAX DisplayString
			MAX-ACCESS read-only
			STATUS current
			DESCRIPTION
				"Get the MEZZ silk-screen."
			::= { blade13MezzEntry 2 }
		
		b13MezzInfo OBJECT-TYPE
			SYNTAX DisplayString
			MAX-ACCESS read-only
			STATUS current
			DESCRIPTION
				"Get the MEZZ description of type."
			::= { blade13MezzEntry 3 }
		
		b13MezzPresent OBJECT-TYPE
			SYNTAX INTEGER
			MAX-ACCESS read-only
			STATUS current
			DESCRIPTION
				"Get the MEZZ presence status."
			::= { blade13MezzEntry 4 }
		
		b13MezzHealth OBJECT-TYPE
			SYNTAX INTEGER
			MAX-ACCESS read-only
			STATUS current
			DESCRIPTION
				"Get the MEZZ health status."
			::= { blade13MezzEntry 5 }
		
		b13MezzLocation OBJECT-TYPE
			SYNTAX DisplayString
			MAX-ACCESS read-only
			STATUS current
			DESCRIPTION
				"Get the MEZZ location."
			::= { blade13MezzEntry 6 }
		
		b13MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade13MezzEntry 7 }
		
		blade13DiskTable OBJECT-TYPE
			SYNTAX SEQUENCE OF Blade13DiskEntry
			MAX-ACCESS not-accessible
			STATUS current
			DESCRIPTION
				"A table containing the list of Blade1 FRU information."
			::= { blade13 2009 }
		
		blade13DiskEntry OBJECT-TYPE
			SYNTAX Blade13DiskEntry
			MAX-ACCESS not-accessible
			STATUS current
			DESCRIPTION
				"Information about a particular current FRU."
			INDEX { b13DiskIndex }
			::= { blade13DiskTable 1 }
		
		Blade13DiskEntry ::=
			SEQUENCE { 
				b13DiskIndex
					INTEGER,
				b13DiskMark
					DisplayString,
				b13DiskInfo
					DisplayString,
				b13DiskPresent
					INTEGER,
				b13DiskHealth
					INTEGER,
				b13DiskLocation
					DisplayString
			 }

		b13DiskIndex OBJECT-TYPE
			SYNTAX INTEGER
			MAX-ACCESS not-accessible
			STATUS current
			DESCRIPTION
				"DISK INDEX"
			::= { blade13DiskEntry 1 }
		
		b13DiskMark OBJECT-TYPE
			SYNTAX DisplayString
			MAX-ACCESS read-only
			STATUS current
			DESCRIPTION
				"Get the disk silk-screen."
			::= { blade13DiskEntry 2 }
		
		b13DiskInfo OBJECT-TYPE
			SYNTAX DisplayString
			MAX-ACCESS read-only
			STATUS current
			DESCRIPTION
				"Get the disk description of vendor, capacity and speed."
			::= { blade13DiskEntry 3 }
		
		b13DiskPresent OBJECT-TYPE
			SYNTAX INTEGER
			MAX-ACCESS read-only
			STATUS current
			DESCRIPTION
				"Get the disk presence status."
			::= { blade13DiskEntry 4 }
		
		b13DiskHealth OBJECT-TYPE
			SYNTAX INTEGER
			MAX-ACCESS read-only
			STATUS current
			DESCRIPTION
				"Get the disk health status."
			::= { blade13DiskEntry 5 }
		
		b13DiskLocation OBJECT-TYPE
			SYNTAX DisplayString
			MAX-ACCESS read-only
			STATUS current
			DESCRIPTION
				"Get the disk location."
			::= { blade13DiskEntry 6 }
		
		blade13SecretKvmVmmTable OBJECT-TYPE
			SYNTAX SEQUENCE OF Blade13SecretKvmVmmEntry
			MAX-ACCESS not-accessible
			STATUS current
			DESCRIPTION
				"A table containing the list of Blade13 KVM&VMM secret information."
			::= { blade13 2010 }

		blade13SecretKvmVmmEntry OBJECT-TYPE
			SYNTAX Blade13SecretKvmVmmEntry
			MAX-ACCESS not-accessible
			STATUS current
			DESCRIPTION
				"Information about a particular current KVM&VMM."
			INDEX { b13SecretKvmVmmIndex }
			::= { blade13SecretKvmVmmTable 1 }
		Blade13SecretKvmVmmEntry ::=
			SEQUENCE { 
				b13SecretKvmVmmIndex
					INTEGER,
				b13SecretKvmState
					INTEGER,
				b13SecretVmmState
					INTEGER,
				b13MMSecretVmmKey
					DisplayString,
				b13SecretVmmKey
					DisplayString
			 }
		b13SecretKvmVmmIndex OBJECT-TYPE
			SYNTAX INTEGER
			MAX-ACCESS not-accessible
			STATUS current
			DESCRIPTION
				"KVM&VMM INDEX."
			::= { blade13SecretKvmVmmEntry 1 }
		b13SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade13SecretKvmVmmEntry 2 }
		b13SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade13SecretKvmVmmEntry 3 }
		b13MMSecretVmmKey OBJECT-TYPE
			SYNTAX DisplayString
			MAX-ACCESS read-only
			STATUS current
			DESCRIPTION
				"Get the MM secret VMM key."
			::= { blade13SecretKvmVmmEntry 4 }
		b13SecretVmmKey OBJECT-TYPE
			SYNTAX DisplayString
			MAX-ACCESS read-write
			STATUS current
			DESCRIPTION
				"Set the secret VMM key."
			::= { blade13SecretKvmVmmEntry 5 }
		blade14 OBJECT IDENTIFIER ::= { blades 14 }

		
 		b14DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade14 4 }
		
 		b14PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade14 5 }
		
 		b14Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade14 6 }

		
 		b14Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade14 8 }
		
 		b14HealthEvents OBJECT-TYPE
			SYNTAX DisplayString
			MAX-ACCESS read-only
			STATUS current
			DESCRIPTION
				"Events that contribute to the b14Health of the b14Location.  
				This is a list of events currently happening on the 
				b14Location."
			::= { blade14 9 }
		
 		b14ClearSEL OBJECT-TYPE
			SYNTAX INTEGER { clear(1) }
			MAX-ACCESS read-write
			STATUS current
			DESCRIPTION
				"Clean the BMC's SEL on the board."
			::= { blade14 12 }
		
 		b14ExDiskBoardPresence OBJECT-TYPE
			SYNTAX INTEGER
				{
				not-present(0),
				present(1)
				}
			MAX-ACCESS read-only
			STATUS current
			DESCRIPTION
				"Used to find out if the extended disk board is present.
				0 - not present
				1 - present"
			::= { blade14 14 }
		
 		b14BladeVersion OBJECT-TYPE
			SYNTAX DisplayString
			MAX-ACCESS read-only
			STATUS current
			DESCRIPTION
				"display the Version of board14."
			::= { blade14 20 }
		
 		b14MACAddress OBJECT-TYPE
			SYNTAX DisplayString
			MAX-ACCESS read-only
			STATUS current
			DESCRIPTION
				"display the MACAddress of board14."
			::= { blade14 21 }
		
		
 		b14Safepwofftime OBJECT-TYPE
			SYNTAX INTEGER
			MAX-ACCESS read-write
			STATUS current
			DESCRIPTION
				"the safe poweroff time.
				"
			::= { blade14 26 }
		
 		b14BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade14 32 }
		
 		b14Systeminfo OBJECT-TYPE
			SYNTAX DisplayString
			MAX-ACCESS read-write
			STATUS current
			DESCRIPTION
				"display the system information of board14."
			::= { blade14 36 }

		
 		b14SystemProperties OBJECT-TYPE
			SYNTAX DisplayString
			MAX-ACCESS read-only
			STATUS current
			DESCRIPTION
				"Get the power of blade1."
			::= { blade14 39 }
		
 		b14BiosCfg OBJECT-TYPE
			SYNTAX DisplayString
			MAX-ACCESS read-write
			STATUS current
			DESCRIPTION
				"Get the power of blade1."
			::= { blade14 40 }
		
 		b14WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade14 41 }
		
 		b14RealTimePower OBJECT-TYPE
			SYNTAX INTEGER
			MAX-ACCESS read-only
			STATUS current
			DESCRIPTION
				" "
			::= { blade14 43 }
		
 		b14PowerCapping OBJECT-TYPE
			SYNTAX DisplayString
			MAX-ACCESS read-write
			STATUS current
			DESCRIPTION
				" "
			::= { blade14 44 }
		
 		b14Powerreference OBJECT-TYPE
			SYNTAX INTEGER
			MAX-ACCESS read-only
			STATUS current
			DESCRIPTION
				" "
			::= { blade14 45 }
		
 		b14ClearBiosConfig OBJECT-TYPE
			SYNTAX INTEGER
			MAX-ACCESS read-write
			STATUS current
			DESCRIPTION
				" "
			::= { blade14 46 }
		
 		b14BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade14 47 }
		
 		b14BmcUserAdd OBJECT-TYPE
			SYNTAX DisplayString
			MAX-ACCESS read-write
			STATUS current
			DESCRIPTION
				"Used to Add the BMC User
				settable format:
				username,passwd"
			::= { blade14 48 }
		
 		b14BmcUserDel OBJECT-TYPE
			SYNTAX DisplayString
			MAX-ACCESS read-write
			STATUS current
			DESCRIPTION
				"Used to Del the BMC User
				settable format:
				username"
			::= { blade14 49 }
		
 		b14BmcUserPasswd OBJECT-TYPE
			SYNTAX DisplayString
			MAX-ACCESS read-write
			STATUS current
			DESCRIPTION
				"Used to Change the BMC User Passwd
				settable format:
				username,passwd"
			::= { blade14 50 }
		
 		b14BmcUserpropertychg OBJECT-TYPE
			SYNTAX DisplayString
			MAX-ACCESS read-write
			STATUS current
			DESCRIPTION
				"Used to Change the BMC User Property
				settable format:
				username,property"
			::= { blade14 51 }
		
 		b14BmcGateway OBJECT-TYPE
			SYNTAX DisplayString
			MAX-ACCESS read-write
			STATUS current
			DESCRIPTION
				"Read or set the gateway."
			::= { blade14 52 }
		
 		b14SlotBitmap OBJECT-TYPE
			SYNTAX INTEGER
			MAX-ACCESS read-only
			STATUS current
			DESCRIPTION
				" "
			::= { blade14 55 }
		
		b14systemGuid OBJECT-TYPE
			SYNTAX DisplayString
			MAX-ACCESS read-only
			STATUS current
			DESCRIPTION
				" "
			::= { blade14 56 }
		
		b14ProductName OBJECT-TYPE
			SYNTAX DisplayString
			MAX-ACCESS read-only
			STATUS current
			DESCRIPTION
				"display the Version of board14."
			::= { blade14 57 }
		
		b14BundleVersion OBJECT-TYPE
			SYNTAX DisplayString
			MAX-ACCESS read-write
			STATUS current
			DESCRIPTION
				"Get or set the board14 bundle version."
			::= { blade14 58 }

 		blade14SensorTargetTable OBJECT-TYPE
			SYNTAX SEQUENCE OF Blade14SensorTargetEntry
			MAX-ACCESS not-accessible
			STATUS current
			DESCRIPTION
				"A table containing the list of sensor information."
			::= { blade14 2001 }
		
 		blade14SensorTargetEntry OBJECT-TYPE
			SYNTAX Blade14SensorTargetEntry
			MAX-ACCESS not-accessible
			STATUS current
			DESCRIPTION
				"Information about a particular current sensor."
			INDEX { b14Target }
			::= { blade14SensorTargetTable 1 }
		
		Blade14SensorTargetEntry ::=
			SEQUENCE { 
				b14Target
					DisplayString,
				b14Current
					DisplayString,
				b14ThresholdsAll
					DisplayString,
				b14UpperCritical
					DisplayString,
				b14UpperNonCritical
					DisplayString,
				b14UpperNonRecoverable
					DisplayString,
				b14LowerNonCritical
					DisplayString,
				b14LowerCritical
					DisplayString,
				b14LowerNonRecoverable
					DisplayString,
				b14SensorHealth
					INTEGER,
				b14SensorHealthEvents
					DisplayString,
				b14NegativeHysteresis
					DisplayString,
				b14PositiveHysteresis
					DisplayString,
				b14SensorType
					DisplayString,
				b14SensorFRUInfo
					DisplayString
			 }

 		b14Target OBJECT-TYPE
			SYNTAX DisplayString
			MAX-ACCESS not-accessible
			STATUS current
			DESCRIPTION
				"sensor Name"
			::= { blade14SensorTargetEntry 1 }
		
 		b14Current OBJECT-TYPE
			SYNTAX DisplayString
			MAX-ACCESS read-only
			STATUS current
			DESCRIPTION
				"Display the current value of a sensor."
			::= { blade14SensorTargetEntry 2 }
		
 		b14ThresholdsAll OBJECT-TYPE
			SYNTAX DisplayString
			MAX-ACCESS read-only
			STATUS current
			DESCRIPTION
				"All thresholds of a sensor"
			::= { blade14SensorTargetEntry 3 }
		
 		b14UpperCritical OBJECT-TYPE
			SYNTAX DisplayString
			MAX-ACCESS read-write
			STATUS current
			DESCRIPTION
				"Upper critical thresholds"
			::= { blade14SensorTargetEntry 4 }
		
 		b14UpperNonCritical OBJECT-TYPE
			SYNTAX DisplayString
			MAX-ACCESS read-write
			STATUS current
			DESCRIPTION
				"Upper non-critical thresholds"
			::= { blade14SensorTargetEntry 5 }
		
 		b14UpperNonRecoverable OBJECT-TYPE
			SYNTAX DisplayString
			MAX-ACCESS read-write
			STATUS current
			DESCRIPTION
				"Upper non-recoverable thresholds"
			::= { blade14SensorTargetEntry 6 }
		
 		b14LowerNonCritical OBJECT-TYPE
			SYNTAX DisplayString
			MAX-ACCESS read-write
			STATUS current
			DESCRIPTION
				"Lower non-critical thresholds"
			::= { blade14SensorTargetEntry 7 }
		
 		b14LowerCritical OBJECT-TYPE
			SYNTAX DisplayString
			MAX-ACCESS read-write
			STATUS current
			DESCRIPTION
				"Lower critical thresholds"
			::= { blade14SensorTargetEntry 8 }
		
 		b14LowerNonRecoverable OBJECT-TYPE
			SYNTAX DisplayString
			MAX-ACCESS read-write
			STATUS current
			DESCRIPTION
				"Lower non-recoverable thresholds"
			::= { blade14SensorTargetEntry 9 }
		
 		b14SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade14SensorTargetEntry 10 }
		
 		b14SensorHealthEvents OBJECT-TYPE
			SYNTAX DisplayString
			MAX-ACCESS read-only
			STATUS current
			DESCRIPTION
				"Events that contribute to the b14Health of the b14Location.  
				This is a list of events currently happening on the 
				b14Location."
			::= { blade14SensorTargetEntry 11 }
		
		
 		b14NegativeHysteresis OBJECT-TYPE
			SYNTAX DisplayString
			MAX-ACCESS read-write
			STATUS current
			DESCRIPTION
				"Get/Set the negativeHysteresis value"
			::= { blade14SensorTargetEntry 16 }
		
 		b14PositiveHysteresis OBJECT-TYPE
			SYNTAX DisplayString
			MAX-ACCESS read-write
			STATUS current
			DESCRIPTION
				"Get/Set the positiveHysteresis value."
			::= { blade14SensorTargetEntry 17 }
		
 		b14SensorType OBJECT-TYPE
			SYNTAX DisplayString
			MAX-ACCESS read-only
			STATUS current
			DESCRIPTION
				"Get the type of the sensor."
			::= { blade14SensorTargetEntry 18 }
		
 		b14SensorFRUInfo OBJECT-TYPE
			SYNTAX DisplayString
			MAX-ACCESS read-only
			STATUS current
			DESCRIPTION
				"Get the fruinfo of the sensor."
			::= { blade14SensorTargetEntry 19 }
		
 		blade14FruTable OBJECT-TYPE
			SYNTAX SEQUENCE OF Blade14FruEntry
			MAX-ACCESS not-accessible
			STATUS current
			DESCRIPTION
				"A table containing the list of FRU information."
			::= { blade14 2002 }
		
 		blade14FruEntry OBJECT-TYPE
			SYNTAX Blade14FruEntry
			MAX-ACCESS not-accessible
			STATUS current
			DESCRIPTION
				"Information about a particular current FRU."
			INDEX { b14fruNumber }
			::= { blade14FruTable 1 }
		
		Blade14FruEntry ::=
			SEQUENCE { 
				b14fruNumber
					INTEGER,
				b14FruHotSwapState
					DisplayString,
				b14FruLedProperties
					DisplayString,
				b14FRUControl
					INTEGER,
				b14FRULabel
					DisplayString,
				b14ResetReason
					DisplayString
			 }

 		b14fruNumber OBJECT-TYPE
			SYNTAX INTEGER
			MAX-ACCESS not-accessible
			STATUS current
			DESCRIPTION
				" "
			::= { blade14FruEntry 1 }
		
 		b14FruHotSwapState OBJECT-TYPE
			SYNTAX DisplayString
			MAX-ACCESS read-only
			STATUS current
			DESCRIPTION
				"Retrieve the hot swap state of the FRU from the 
				internally known hot swap states of blade14."
			::= { blade14FruEntry 3 }
		
 		b14FruLedProperties OBJECT-TYPE
			SYNTAX DisplayString
			MAX-ACCESS read-only
			STATUS current
			DESCRIPTION
				"Retrieves the LED support information from a FRU. Returns a comma separated
				list of LEDS and the number of FRU supported user LEDs."
			::= { blade14FruEntry 4 }

		

		b14FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade14FruEntry 9 }
		
 		b14FRULabel OBJECT-TYPE
			SYNTAX DisplayString
			MAX-ACCESS read-only
			STATUS current
			DESCRIPTION
				"Get fru label of blade14."
			::= { blade14FruEntry 10 }
		
 		b14ResetReason OBJECT-TYPE
			SYNTAX DisplayString
			MAX-ACCESS read-only
			STATUS current
			DESCRIPTION
				"Delete fru label of smm."
			::= { blade14FruEntry 11 }
		
 		blade14FruLedTable OBJECT-TYPE
			SYNTAX SEQUENCE OF Blade14FruLedEntry
			MAX-ACCESS not-accessible
			STATUS current
			DESCRIPTION
				"A table containing the list of led information."
			::= { blade14 2003 }
		
 		blade14FruLedEntry OBJECT-TYPE
			SYNTAX Blade14FruLedEntry
			MAX-ACCESS not-accessible
			STATUS current
			DESCRIPTION
				"Information about a particular current led."
			INDEX { b14FruID, b14FruLed }
			::= { blade14FruLedTable 1 }
		
		Blade14FruLedEntry ::=
			SEQUENCE { 
				b14FruID
					INTEGER,
				b14FruLed
					DisplayString,
				b14FruLedColorProps
					DisplayString,
				b14FruLedState
					DisplayString
			 }

 		b14FruID OBJECT-TYPE
			SYNTAX INTEGER
			MAX-ACCESS not-accessible
			STATUS current
			DESCRIPTION
				" "
			::= { blade14FruLedEntry 1 }
		
 		b14FruLed OBJECT-TYPE
			SYNTAX DisplayString
			MAX-ACCESS not-accessible
			STATUS current
			DESCRIPTION
				" "
			::= { blade14FruLedEntry 2 }
		
 		b14FruLedColorProps OBJECT-TYPE
			SYNTAX DisplayString
			MAX-ACCESS read-only
			STATUS current
			DESCRIPTION
				"Finds out what colors are supported by the LED"
			::= { blade14FruLedEntry 3 }
		
 		b14FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade14FruLedEntry 4 }
		
 		blade14FruDescriptionTable OBJECT-TYPE
			SYNTAX SEQUENCE OF Blade14FruDescriptionEntry
			MAX-ACCESS not-accessible
			STATUS current
			DESCRIPTION
				"A table containing the list of blade14 FRU information."
			::= { blade14 2004 }
		
 		blade14FruDescriptionEntry OBJECT-TYPE
			SYNTAX Blade14FruDescriptionEntry
			MAX-ACCESS not-accessible
			STATUS current
			DESCRIPTION
				"Information about a particular current FRU."
			INDEX { b14fruNum }
			::= { blade14FruDescriptionTable 1 }
		
		Blade14FruDescriptionEntry ::=
			SEQUENCE { 
				b14fruNum
					INTEGER,
				b14fruBoardDescription
					DisplayString,
				b14fruBoardManufacturer
					DisplayString,
				b14fruBoardPartNumber
					DisplayString,
				b14fruBoardSerialNumber
					DisplayString,
				b14fruBoardManufactureDate
					DisplayString,
				b14fruProductDescription
					DisplayString,
				b14fruProductManufacturer
					DisplayString,
				b14fruProductPartNumber
					DisplayString,
				b14fruProductSerialNumber
					DisplayString,
				b14fruProductRevision
					DisplayString,
				b14fruAll
					DisplayString
			 }

 		b14fruNum OBJECT-TYPE
			SYNTAX INTEGER
			MAX-ACCESS not-accessible
			STATUS current
			DESCRIPTION
				"blade14 FRU's INDEX"
			::= { blade14FruDescriptionEntry 1 }
		
 		b14fruBoardDescription OBJECT-TYPE
			SYNTAX DisplayString
			MAX-ACCESS read-only
			STATUS current
			DESCRIPTION
				"Used to read the Board Description from the blade14 fru."
			::= { blade14FruDescriptionEntry 2 }
		
 		b14fruBoardManufacturer OBJECT-TYPE
			SYNTAX DisplayString
			MAX-ACCESS read-only
			STATUS current
			DESCRIPTION
				"Used to read the Board Manufacturer from the bladef14 fru."
			::= { blade14FruDescriptionEntry 3 }
		
 		b14fruBoardPartNumber OBJECT-TYPE
			SYNTAX DisplayString
			MAX-ACCESS read-only
			STATUS current
			DESCRIPTION
				"Used to read the Board Part Number from the blade14 fru."
			::= { blade14FruDescriptionEntry 4 }
		
 		b14fruBoardSerialNumber OBJECT-TYPE
			SYNTAX DisplayString
			MAX-ACCESS read-only
			STATUS current
			DESCRIPTION
				"Used to read the Board Serial Number from the blade14 fru."
			::= { blade14FruDescriptionEntry 5 }
		
 		b14fruBoardManufactureDate OBJECT-TYPE
			SYNTAX DisplayString
			MAX-ACCESS read-only
			STATUS current
			DESCRIPTION
				"Used to read the Board Manufacture Date from the blade14 fru."
			::= { blade14FruDescriptionEntry 6 }
		
 		b14fruProductDescription OBJECT-TYPE
			SYNTAX DisplayString
			MAX-ACCESS read-only
			STATUS current
			DESCRIPTION
				"Used to read the Product Description from the blade14 fru."
			::= { blade14FruDescriptionEntry 7 }
		
 		b14fruProductManufacturer OBJECT-TYPE
			SYNTAX DisplayString
			MAX-ACCESS read-only
			STATUS current
			DESCRIPTION
				"Used to read the Product Manufacturer from the blade14 fru."
			::= { blade14FruDescriptionEntry 8 }
		
 		b14fruProductPartNumber OBJECT-TYPE
			SYNTAX DisplayString
			MAX-ACCESS read-only
			STATUS current
			DESCRIPTION
				"Used to read the Product Part Number from the blade14 fru."
			::= { blade14FruDescriptionEntry 9 }
		
 		b14fruProductSerialNumber OBJECT-TYPE
			SYNTAX DisplayString
			MAX-ACCESS read-only
			STATUS current
			DESCRIPTION
				"Used to read the Product Serial Number from the blade14 fru."
			::= { blade14FruDescriptionEntry 10 }
		
 		b14fruProductRevision OBJECT-TYPE
			SYNTAX DisplayString
			MAX-ACCESS read-only
			STATUS current
			DESCRIPTION
				"Used to read the Product Revision from the blade14 fru."
			::= { blade14FruDescriptionEntry 13 }
		
 		b14fruAll OBJECT-TYPE
			SYNTAX DisplayString
			MAX-ACCESS read-only
			STATUS current
			DESCRIPTION
				"Used to read the fru info all."
			::= { blade14FruDescriptionEntry 14 }
		
		blade14CPUTable OBJECT-TYPE
			SYNTAX SEQUENCE OF Blade14CPUEntry
			MAX-ACCESS not-accessible
			STATUS current
			DESCRIPTION
				"A table containing the list of Blade1 FRU information."
			::= { blade14 2006 }
		
		blade14CPUEntry OBJECT-TYPE
			SYNTAX Blade14CPUEntry
			MAX-ACCESS not-accessible
			STATUS current
			DESCRIPTION
				"Information about a particular current FRU."
			INDEX { b14CPUIndex }
			::= { blade14CPUTable 1 }
		
		Blade14CPUEntry ::=
			SEQUENCE { 
				b14CPUIndex
					INTEGER,
				b14CPUMark
					DisplayString,
				b14CPUInfo
					DisplayString,
				b14CPUPresent
					INTEGER,
				b14CPUHealth
					INTEGER,
				b14CPULocation
					DisplayString
			 }

		b14CPUIndex OBJECT-TYPE
			SYNTAX INTEGER
			MAX-ACCESS not-accessible
			STATUS current
			DESCRIPTION
				"CPU INDEX"
			::= { blade14CPUEntry 1 }
		
		b14CPUMark OBJECT-TYPE
			SYNTAX DisplayString
			MAX-ACCESS read-only
			STATUS current
			DESCRIPTION
				"Get the CPU silk-screen."
			::= { blade14CPUEntry 2 }
		
		b14CPUInfo OBJECT-TYPE
			SYNTAX DisplayString
			MAX-ACCESS read-only
			STATUS current
			DESCRIPTION
				"Get the CPU description of vendor, type and frequency."
			::= { blade14CPUEntry 3 }
		
		b14CPUPresent OBJECT-TYPE
			SYNTAX INTEGER
			MAX-ACCESS read-only
			STATUS current
			DESCRIPTION
				"Get the CPU presence status."
			::= { blade14CPUEntry 4 }
		
		b14CPUHealth OBJECT-TYPE
			SYNTAX INTEGER
			MAX-ACCESS read-only
			STATUS current
			DESCRIPTION
				"Get the CPU health status."
			::= { blade14CPUEntry 5 }
		
		b14CPULocation OBJECT-TYPE
			SYNTAX DisplayString
			MAX-ACCESS read-only
			STATUS current
			DESCRIPTION
				"Get the CPU location."
			::= { blade14CPUEntry 6 }
		
		blade14MemoryTable OBJECT-TYPE
			SYNTAX SEQUENCE OF Blade14MemoryEntry
			MAX-ACCESS not-accessible
			STATUS current
			DESCRIPTION
				"A table containing the list of Blade1 FRU information."
			::= { blade14 2007 }
		
		blade14MemoryEntry OBJECT-TYPE
			SYNTAX Blade14MemoryEntry
			MAX-ACCESS not-accessible
			STATUS current
			DESCRIPTION
				"Information about a particular current FRU."
			INDEX { b14MEMIndex }
			::= { blade14MemoryTable 1 }
		
		Blade14MemoryEntry ::=
			SEQUENCE { 
				b14MEMIndex
					INTEGER,
				b14MEMMark
					DisplayString,
				b14MEMInfo
					DisplayString,
				b14MEMPresent
					INTEGER,
				b14MEMHealth
					INTEGER,
				b14MEMLocation
					DisplayString
			 }

		b14MEMIndex OBJECT-TYPE
			SYNTAX INTEGER
			MAX-ACCESS not-accessible
			STATUS current
			DESCRIPTION
				"MEMORY INDEX"
			::= { blade14MemoryEntry 1 }
		
		b14MEMMark OBJECT-TYPE
			SYNTAX DisplayString
			MAX-ACCESS read-only
			STATUS current
			DESCRIPTION
				"Get the memory silk-screen."
			::= { blade14MemoryEntry 2 }
		
		b14MEMInfo OBJECT-TYPE
			SYNTAX DisplayString
			MAX-ACCESS read-only
			STATUS current
			DESCRIPTION
				"Get the memory description of vendor, frequency and capacity."
			::= { blade14MemoryEntry 3 }
		
		b14MEMPresent OBJECT-TYPE
			SYNTAX INTEGER
			MAX-ACCESS read-only
			STATUS current
			DESCRIPTION
				"Get the memory presence status."
			::= { blade14MemoryEntry 4 }
		
		b14MEMHealth OBJECT-TYPE
			SYNTAX INTEGER
			MAX-ACCESS read-only
			STATUS current
			DESCRIPTION
				"Get the memory health status."
			::= { blade14MemoryEntry 5 }
		
		b14MEMLocation OBJECT-TYPE
			SYNTAX DisplayString
			MAX-ACCESS read-only
			STATUS current
			DESCRIPTION
				"Get the memory location."
			::= { blade14MemoryEntry 6 }
		
		blade14MezzTable OBJECT-TYPE
			SYNTAX SEQUENCE OF Blade14MezzEntry
			MAX-ACCESS not-accessible
			STATUS current
			DESCRIPTION
				"A table containing the list of Blade1 FRU information."
			::= { blade14 2008 }
		
		blade14MezzEntry OBJECT-TYPE
			SYNTAX Blade14MezzEntry
			MAX-ACCESS not-accessible
			STATUS current
			DESCRIPTION
				"Information about a particular current FRU."
			INDEX { b14MezzIndex }
			::= { blade14MezzTable 1 }
		
		Blade14MezzEntry ::=
			SEQUENCE { 
				b14MezzIndex
					INTEGER,
				b14MezzMark
					DisplayString,
				b14MezzInfo
					DisplayString,
				b14MezzPresent
					INTEGER,
				b14MezzHealth
					INTEGER,
				b14MezzLocation
					DisplayString,
				b14MezzMac
					DisplayString
			 }

		b14MezzIndex OBJECT-TYPE
			SYNTAX INTEGER
			MAX-ACCESS not-accessible
			STATUS current
			DESCRIPTION
				"MEZZ INDEX"
			::= { blade14MezzEntry 1 }
		
		b14MezzMark OBJECT-TYPE
			SYNTAX DisplayString
			MAX-ACCESS read-only
			STATUS current
			DESCRIPTION
				"Get the MEZZ silk-screen."
			::= { blade14MezzEntry 2 }
		
		b14MezzInfo OBJECT-TYPE
			SYNTAX DisplayString
			MAX-ACCESS read-only
			STATUS current
			DESCRIPTION
				"Get the MEZZ description of type."
			::= { blade14MezzEntry 3 }
		
		b14MezzPresent OBJECT-TYPE
			SYNTAX INTEGER
			MAX-ACCESS read-only
			STATUS current
			DESCRIPTION
				"Get the MEZZ presence status."
			::= { blade14MezzEntry 4 }
		
		b14MezzHealth OBJECT-TYPE
			SYNTAX INTEGER
			MAX-ACCESS read-only
			STATUS current
			DESCRIPTION
				"Get the MEZZ health status."
			::= { blade14MezzEntry 5 }
		
		b14MezzLocation OBJECT-TYPE
			SYNTAX DisplayString
			MAX-ACCESS read-only
			STATUS current
			DESCRIPTION
				"Get the MEZZ location."
			::= { blade14MezzEntry 6 }
		
		b14MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade14MezzEntry 7 }
		
		blade14DiskTable OBJECT-TYPE
			SYNTAX SEQUENCE OF Blade14DiskEntry
			MAX-ACCESS not-accessible
			STATUS current
			DESCRIPTION
				"A table containing the list of Blade1 FRU information."
			::= { blade14 2009 }
		
		blade14DiskEntry OBJECT-TYPE
			SYNTAX Blade14DiskEntry
			MAX-ACCESS not-accessible
			STATUS current
			DESCRIPTION
				"Information about a particular current FRU."
			INDEX { b14DiskIndex }
			::= { blade14DiskTable 1 }
		
		Blade14DiskEntry ::=
			SEQUENCE { 
				b14DiskIndex
					INTEGER,
				b14DiskMark
					DisplayString,
				b14DiskInfo
					DisplayString,
				b14DiskPresent
					INTEGER,
				b14DiskHealth
					INTEGER,
				b14DiskLocation
					DisplayString
			 }

		b14DiskIndex OBJECT-TYPE
			SYNTAX INTEGER
			MAX-ACCESS not-accessible
			STATUS current
			DESCRIPTION
				"DISK INDEX"
			::= { blade14DiskEntry 1 }
		
		b14DiskMark OBJECT-TYPE
			SYNTAX DisplayString
			MAX-ACCESS read-only
			STATUS current
			DESCRIPTION
				"Get the disk silk-screen."
			::= { blade14DiskEntry 2 }
		
		b14DiskInfo OBJECT-TYPE
			SYNTAX DisplayString
			MAX-ACCESS read-only
			STATUS current
			DESCRIPTION
				"Get the disk description of vendor, capacity and speed."
			::= { blade14DiskEntry 3 }
		
		b14DiskPresent OBJECT-TYPE
			SYNTAX INTEGER
			MAX-ACCESS read-only
			STATUS current
			DESCRIPTION
				"Get the disk presence status."
			::= { blade14DiskEntry 4 }
		
		b14DiskHealth OBJECT-TYPE
			SYNTAX INTEGER
			MAX-ACCESS read-only
			STATUS current
			DESCRIPTION
				"Get the disk health status."
			::= { blade14DiskEntry 5 }
		
		b14DiskLocation OBJECT-TYPE
			SYNTAX DisplayString
			MAX-ACCESS read-only
			STATUS current
			DESCRIPTION
				"Get the disk location."
			::= { blade14DiskEntry 6 }
		
		blade14SecretKvmVmmTable OBJECT-TYPE
			SYNTAX SEQUENCE OF Blade14SecretKvmVmmEntry
			MAX-ACCESS not-accessible
			STATUS current
			DESCRIPTION
				"A table containing the list of Blade14 KVM&VMM secret information."
			::= { blade14 2010 }

		blade14SecretKvmVmmEntry OBJECT-TYPE
			SYNTAX Blade14SecretKvmVmmEntry
			MAX-ACCESS not-accessible
			STATUS current
			DESCRIPTION
				"Information about a particular current KVM&VMM."
			INDEX { b14SecretKvmVmmIndex }
			::= { blade14SecretKvmVmmTable 1 }
		Blade14SecretKvmVmmEntry ::=
			SEQUENCE { 
				b14SecretKvmVmmIndex
					INTEGER,
				b14SecretKvmState
					INTEGER,
				b14SecretVmmState
					INTEGER,
				b14MMSecretVmmKey
					DisplayString,
				b14SecretVmmKey
					DisplayString
			 }
		b14SecretKvmVmmIndex OBJECT-TYPE
			SYNTAX INTEGER
			MAX-ACCESS not-accessible
			STATUS current
			DESCRIPTION
				"KVM&VMM INDEX."
			::= { blade14SecretKvmVmmEntry 1 }
		b14SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade14SecretKvmVmmEntry 2 }
		b14SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade14SecretKvmVmmEntry 3 }
		b14MMSecretVmmKey OBJECT-TYPE
			SYNTAX DisplayString
			MAX-ACCESS read-only
			STATUS current
			DESCRIPTION
				"Get the MM secret VMM key."
			::= { blade14SecretKvmVmmEntry 4 }
		b14SecretVmmKey OBJECT-TYPE
			SYNTAX DisplayString
			MAX-ACCESS read-write
			STATUS current
			DESCRIPTION
				"Set the secret VMM key."
			::= { blade14SecretKvmVmmEntry 5 }
		blade15 OBJECT IDENTIFIER ::= { blades 15 }

		
 		b15DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade15 4 }
		
 		b15PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade15 5 }
		
 		b15Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade15 6 }

		
 		b15Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade15 8 }
		
 		b15HealthEvents OBJECT-TYPE
			SYNTAX DisplayString
			MAX-ACCESS read-only
			STATUS current
			DESCRIPTION
				"Events that contribute to the b14Health of the b14Location.  
				This is a list of events currently happening on the 
				b14Location."
			::= { blade15 9 }
		
 		b15ClearSEL OBJECT-TYPE
			SYNTAX INTEGER { clear(1) }
			MAX-ACCESS read-write
			STATUS current
			DESCRIPTION
				"Clean the BMC's SEL on the board."
			::= { blade15 12 }
		
 		b15ExDiskBoardPresence OBJECT-TYPE
			SYNTAX INTEGER
				{
				not-present(0),
				present(1)
				}
			MAX-ACCESS read-only
			STATUS current
			DESCRIPTION
				"Used to find out if the extended disk board is present.
				0 - not present
				1 - present"
			::= { blade15 14 }
		
 		b15BladeVersion OBJECT-TYPE
			SYNTAX DisplayString
			MAX-ACCESS read-only
			STATUS current
			DESCRIPTION
				"display the Version of board14."
			::= { blade15 20 }
		
 		b15MACAddress OBJECT-TYPE
			SYNTAX DisplayString
			MAX-ACCESS read-only
			STATUS current
			DESCRIPTION
				"display the MACAddress of board14."
			::= { blade15 21 }
		
				
							
		
 		b15Safepwofftime OBJECT-TYPE
			SYNTAX INTEGER
			MAX-ACCESS read-write
			STATUS current
			DESCRIPTION
				"the safe poweroff time.
				"
			::= { blade15 26 }
		
 		b15BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]    
				6=Force boot into BIOS Setup
				15=Force boot from Floppy/primary removable media           
				
				"
			::= { blade15 32 }
		
 		b15Systeminfo OBJECT-TYPE
			SYNTAX DisplayString
			MAX-ACCESS read-write
			STATUS current
			DESCRIPTION
				"display the system information of board14."
			::= { blade15 36 }

		
 		b15SystemProperties OBJECT-TYPE
			SYNTAX DisplayString
			MAX-ACCESS read-only
			STATUS current
			DESCRIPTION
				"Get the power of blade1."
			::= { blade15 39 }
		
 		b15BiosCfg OBJECT-TYPE
			SYNTAX DisplayString
			MAX-ACCESS read-write
			STATUS current
			DESCRIPTION
				"Get the power of blade1."
			::= { blade15 40 }
		
 		b15WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade15 41 }
		
 		b15RealTimePower OBJECT-TYPE
			SYNTAX INTEGER
			MAX-ACCESS read-only
			STATUS current
			DESCRIPTION
				" "
			::= { blade15 43 }
		
 		b15PowerCapping OBJECT-TYPE
			SYNTAX DisplayString
			MAX-ACCESS read-write
			STATUS current
			DESCRIPTION
				" "
			::= { blade15 44 }
		
 		b15Powerreference OBJECT-TYPE
			SYNTAX INTEGER
			MAX-ACCESS read-only
			STATUS current
			DESCRIPTION
				" "
			::= { blade15 45 }
		
 		b15ClearBiosConfig OBJECT-TYPE
			SYNTAX INTEGER
			MAX-ACCESS read-write
			STATUS current
			DESCRIPTION
				" "
			::= { blade15 46 }
		
 		b15BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade15 47 }
		
 		b15BmcUserAdd OBJECT-TYPE
			SYNTAX DisplayString
			MAX-ACCESS read-write
			STATUS current
			DESCRIPTION
				"Used to Add the BMC User
				settable format:
				username,passwd"
			::= { blade15 48 }
		
 		b15BmcUserDel OBJECT-TYPE
			SYNTAX DisplayString
			MAX-ACCESS read-write
			STATUS current
			DESCRIPTION
				"Used to Del the BMC User
				settable format:
				username"
			::= { blade15 49 }
		
 		b15BmcUserPasswd OBJECT-TYPE
			SYNTAX DisplayString
			MAX-ACCESS read-write
			STATUS current
			DESCRIPTION
				"Used to Change the BMC User Passwd
				settable format:
				username,passwd"
			::= { blade15 50 }
		
 		b15BmcUserpropertychg OBJECT-TYPE
			SYNTAX DisplayString
			MAX-ACCESS read-write
			STATUS current
			DESCRIPTION
				"Used to Change the BMC User Property
				settable format:
				username,property"
			::= { blade15 51 }
		
 		b15BmcGateway OBJECT-TYPE
			SYNTAX DisplayString
			MAX-ACCESS read-write
			STATUS current
			DESCRIPTION
				"Read or set the gateway."
			::= { blade15 52 }
		
 		b15SlotBitmap OBJECT-TYPE
			SYNTAX INTEGER
			MAX-ACCESS read-only
			STATUS current
			DESCRIPTION
				" "
			::= { blade15 55 }
		
		b15systemGuid OBJECT-TYPE
			SYNTAX DisplayString
			MAX-ACCESS read-only
			STATUS current
			DESCRIPTION
				" "
			::= { blade15 56 }
		
		b15ProductName OBJECT-TYPE
			SYNTAX DisplayString
			MAX-ACCESS read-only
			STATUS current
			DESCRIPTION
				"display the Version of board14."
			::= { blade15 57 }
		
		b15BundleVersion OBJECT-TYPE
			SYNTAX DisplayString
			MAX-ACCESS read-write
			STATUS current
			DESCRIPTION
				"Get or set the board15 bundle version."
			::= { blade15 58 }

 		blade15SensorTargetTable OBJECT-TYPE
			SYNTAX SEQUENCE OF Blade15SensorTargetEntry
			MAX-ACCESS not-accessible
			STATUS current
			DESCRIPTION
				"A table containing the list of sensor information."
			::= { blade15 2001 }
		
 		blade15SensorTargetEntry OBJECT-TYPE
			SYNTAX Blade15SensorTargetEntry
			MAX-ACCESS not-accessible
			STATUS current
			DESCRIPTION
				"Information about a particular current sensor."
			INDEX { b15Target }
			::= { blade15SensorTargetTable 1 }
		
		Blade15SensorTargetEntry ::=
			SEQUENCE { 
				b15Target
					DisplayString,
				b15Current
					DisplayString,
				b15ThresholdsAll
					DisplayString,
				b15UpperCritical
					DisplayString,
				b15UpperNonCritical
					DisplayString,
				b15UpperNonRecoverable
					DisplayString,
				b15LowerNonCritical
					DisplayString,
				b15LowerCritical
					DisplayString,
				b15LowerNonRecoverable
					DisplayString,
				b15SensorHealth
					INTEGER,
				b15SensorHealthEvents
					DisplayString,
				b15NegativeHysteresis
					DisplayString,
				b15PositiveHysteresis
					DisplayString,
				b15SensorType
					DisplayString,
				b15SensorFRUInfo
					DisplayString
			 }

 		b15Target OBJECT-TYPE
			SYNTAX DisplayString
			MAX-ACCESS not-accessible
			STATUS current
			DESCRIPTION
				"sensor Name"
			::= { blade15SensorTargetEntry 1 }
		
 		b15Current OBJECT-TYPE
			SYNTAX DisplayString
			MAX-ACCESS read-only
			STATUS current
			DESCRIPTION
				"Display the current value of a sensor."
			::= { blade15SensorTargetEntry 2 }
		
 		b15ThresholdsAll OBJECT-TYPE
			SYNTAX DisplayString
			MAX-ACCESS read-only
			STATUS current
			DESCRIPTION
				"All thresholds of a sensor"
			::= { blade15SensorTargetEntry 3 }
		
 		b15UpperCritical OBJECT-TYPE
			SYNTAX DisplayString
			MAX-ACCESS read-write
			STATUS current
			DESCRIPTION
				"Upper critical thresholds"
			::= { blade15SensorTargetEntry 4 }
		
 		b15UpperNonCritical OBJECT-TYPE
			SYNTAX DisplayString
			MAX-ACCESS read-write
			STATUS current
			DESCRIPTION
				"Upper non-critical thresholds"
			::= { blade15SensorTargetEntry 5 }
		
 		b15UpperNonRecoverable OBJECT-TYPE
			SYNTAX DisplayString
			MAX-ACCESS read-write
			STATUS current
			DESCRIPTION
				"Upper non-recoverable thresholds"
			::= { blade15SensorTargetEntry 6 }
		
 		b15LowerNonCritical OBJECT-TYPE
			SYNTAX DisplayString
			MAX-ACCESS read-write
			STATUS current
			DESCRIPTION
				"Lower non-critical thresholds"
			::= { blade15SensorTargetEntry 7 }
		
 		b15LowerCritical OBJECT-TYPE
			SYNTAX DisplayString
			MAX-ACCESS read-write
			STATUS current
			DESCRIPTION
				"Lower critical thresholds"
			::= { blade15SensorTargetEntry 8 }
		
 		b15LowerNonRecoverable OBJECT-TYPE
			SYNTAX DisplayString
			MAX-ACCESS read-write
			STATUS current
			DESCRIPTION
				"Lower non-recoverable thresholds"
			::= { blade15SensorTargetEntry 9 }
		
 		b15SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade15SensorTargetEntry 10 }
		
 		b15SensorHealthEvents OBJECT-TYPE
			SYNTAX DisplayString
			MAX-ACCESS read-only
			STATUS current
			DESCRIPTION
				"Events that contribute to the b14Health of the b14Location.  
				This is a list of events currently happening on the 
				b14Location."
			::= { blade15SensorTargetEntry 11 }
		
		
 		b15NegativeHysteresis OBJECT-TYPE
			SYNTAX DisplayString
			MAX-ACCESS read-write
			STATUS current
			DESCRIPTION
				"Get/Set the negativeHysteresis value"
			::= { blade15SensorTargetEntry 16 }
		
 		b15PositiveHysteresis OBJECT-TYPE
			SYNTAX DisplayString
			MAX-ACCESS read-write
			STATUS current
			DESCRIPTION
				"Get/Set the positiveHysteresis value."
			::= { blade15SensorTargetEntry 17 }
		
 		b15SensorType OBJECT-TYPE
			SYNTAX DisplayString
			MAX-ACCESS read-only
			STATUS current
			DESCRIPTION
				"Get the type of the sensor."
			::= { blade15SensorTargetEntry 18 }
		
 		b15SensorFRUInfo OBJECT-TYPE
			SYNTAX DisplayString
			MAX-ACCESS read-only
			STATUS current
			DESCRIPTION
				"Get the fruinfo of the sensor."
			::= { blade15SensorTargetEntry 19 }
		
 		blade15FruTable OBJECT-TYPE
			SYNTAX SEQUENCE OF Blade15FruEntry
			MAX-ACCESS not-accessible
			STATUS current
			DESCRIPTION
				"A table containing the list of FRU information."
			::= { blade15 2002 }
		
 		blade15FruEntry OBJECT-TYPE
			SYNTAX Blade15FruEntry
			MAX-ACCESS not-accessible
			STATUS current
			DESCRIPTION
				"Information about a particular current FRU."
			INDEX { b15fruNumber }
			::= { blade15FruTable 1 }
		
		Blade15FruEntry ::=
			SEQUENCE { 
				b15fruNumber
					INTEGER,
				b15FruHotSwapState
					DisplayString,
				b15FruLedProperties
					DisplayString,
				b15FRUControl
					INTEGER,
				b15FRULabel
					DisplayString,
				b15ResetReason
					DisplayString
			 }

 		b15fruNumber OBJECT-TYPE
			SYNTAX INTEGER
			MAX-ACCESS not-accessible
			STATUS current
			DESCRIPTION
				" "
			::= { blade15FruEntry 1 }
		
 		b15FruHotSwapState OBJECT-TYPE
			SYNTAX DisplayString
			MAX-ACCESS read-only
			STATUS current
			DESCRIPTION
				"Retrieve the hot swap state of the FRU from the 
				internally known hot swap states of blade14."
			::= { blade15FruEntry 3 }
		
 		b15FruLedProperties OBJECT-TYPE
			SYNTAX DisplayString
			MAX-ACCESS read-only
			STATUS current
			DESCRIPTION
				"Retrieves the LED support information from a FRU. Returns a comma separated
				list of LEDS and the number of FRU supported user LEDs."
			::= { blade15FruEntry 4 }

		

		b15FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade15FruEntry 9 }
		
 		b15FRULabel OBJECT-TYPE
			SYNTAX DisplayString
			MAX-ACCESS read-only
			STATUS current
			DESCRIPTION
				"Get fru label of blade14."
			::= { blade15FruEntry 10 }
		
 		b15ResetReason OBJECT-TYPE
			SYNTAX DisplayString
			MAX-ACCESS read-only
			STATUS current
			DESCRIPTION
				"Delete fru label of smm."
			::= { blade15FruEntry 11 }
		
 		blade15FruLedTable OBJECT-TYPE
			SYNTAX SEQUENCE OF Blade15FruLedEntry
			MAX-ACCESS not-accessible
			STATUS current
			DESCRIPTION
				"A table containing the list of led information."
			::= { blade15 2003 }
		
 		blade15FruLedEntry OBJECT-TYPE
			SYNTAX Blade15FruLedEntry
			MAX-ACCESS not-accessible
			STATUS current
			DESCRIPTION
				"Information about a particular current led."
			INDEX { b15FruID, b15FruLed }
			::= { blade15FruLedTable 1 }
		
		Blade15FruLedEntry ::=
			SEQUENCE { 
				b15FruID
					INTEGER,
				b15FruLed
					DisplayString,
				b15FruLedColorProps
					DisplayString,
				b15FruLedState
					DisplayString
			 }

 		b15FruID OBJECT-TYPE
			SYNTAX INTEGER
			MAX-ACCESS not-accessible
			STATUS current
			DESCRIPTION
				" "
			::= { blade15FruLedEntry 1 }
		
 		b15FruLed OBJECT-TYPE
			SYNTAX DisplayString
			MAX-ACCESS not-accessible
			STATUS current
			DESCRIPTION
				" "
			::= { blade15FruLedEntry 2 }
		
 		b15FruLedColorProps OBJECT-TYPE
			SYNTAX DisplayString
			MAX-ACCESS read-only
			STATUS current
			DESCRIPTION
				"Finds out what colors are supported by the LED"
			::= { blade15FruLedEntry 3 }
		
 		b15FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade15FruLedEntry 4 }
		
 		blade15FruDescriptionTable OBJECT-TYPE
			SYNTAX SEQUENCE OF Blade15FruDescriptionEntry
			MAX-ACCESS not-accessible
			STATUS current
			DESCRIPTION
				"A table containing the list of blade14 FRU information."
			::= { blade15 2004 }
		
 		blade15FruDescriptionEntry OBJECT-TYPE
			SYNTAX Blade15FruDescriptionEntry
			MAX-ACCESS not-accessible
			STATUS current
			DESCRIPTION
				"Information about a particular current FRU."
			INDEX { b15fruNum }
			::= { blade15FruDescriptionTable 1 }
		
		Blade15FruDescriptionEntry ::=
			SEQUENCE { 
				b15fruNum
					INTEGER,
				b15fruBoardDescription
					DisplayString,
				b15fruBoardManufacturer
					DisplayString,
				b15fruBoardPartNumber
					DisplayString,
				b15fruBoardSerialNumber
					DisplayString,
				b15fruBoardManufactureDate
					DisplayString,
				b15fruProductDescription
					DisplayString,
				b15fruProductManufacturer
					DisplayString,
				b15fruProductPartNumber
					DisplayString,
				b15fruProductSerialNumber
					DisplayString,
				b15fruProductRevision
					DisplayString,
				b15fruAll
					DisplayString
			 }

 		b15fruNum OBJECT-TYPE
			SYNTAX INTEGER
			MAX-ACCESS not-accessible
			STATUS current
			DESCRIPTION
				"blade14 FRU's INDEX"
			::= { blade15FruDescriptionEntry 1 }
		
 		b15fruBoardDescription OBJECT-TYPE
			SYNTAX DisplayString
			MAX-ACCESS read-only
			STATUS current
			DESCRIPTION
				"Used to read the Board Description from the blade14 fru."
			::= { blade15FruDescriptionEntry 2 }
		
 		b15fruBoardManufacturer OBJECT-TYPE
			SYNTAX DisplayString
			MAX-ACCESS read-only
			STATUS current
			DESCRIPTION
				"Used to read the Board Manufacturer from the bladef14 fru."
			::= { blade15FruDescriptionEntry 3 }
		
 		b15fruBoardPartNumber OBJECT-TYPE
			SYNTAX DisplayString
			MAX-ACCESS read-only
			STATUS current
			DESCRIPTION
				"Used to read the Board Part Number from the blade14 fru."
			::= { blade15FruDescriptionEntry 4 }
		
 		b15fruBoardSerialNumber OBJECT-TYPE
			SYNTAX DisplayString
			MAX-ACCESS read-only
			STATUS current
			DESCRIPTION
				"Used to read the Board Serial Number from the blade14 fru."
			::= { blade15FruDescriptionEntry 5 }
		
 		b15fruBoardManufactureDate OBJECT-TYPE
			SYNTAX DisplayString
			MAX-ACCESS read-only
			STATUS current
			DESCRIPTION
				"Used to read the Board Manufacture Date from the blade14 fru."
			::= { blade15FruDescriptionEntry 6 }
		
 		b15fruProductDescription OBJECT-TYPE
			SYNTAX DisplayString
			MAX-ACCESS read-only
			STATUS current
			DESCRIPTION
				"Used to read the Product Description from the blade14 fru."
			::= { blade15FruDescriptionEntry 7 }
		
 		b15fruProductManufacturer OBJECT-TYPE
			SYNTAX DisplayString
			MAX-ACCESS read-only
			STATUS current
			DESCRIPTION
				"Used to read the Product Manufacturer from the blade14 fru."
			::= { blade15FruDescriptionEntry 8 }
		
 		b15fruProductPartNumber OBJECT-TYPE
			SYNTAX DisplayString
			MAX-ACCESS read-only
			STATUS current
			DESCRIPTION
				"Used to read the Product Part Number from the blade14 fru."
			::= { blade15FruDescriptionEntry 9 }
		
 		b15fruProductSerialNumber OBJECT-TYPE
			SYNTAX DisplayString
			MAX-ACCESS read-only
			STATUS current
			DESCRIPTION
				"Used to read the Product Serial Number from the blade14 fru."
			::= { blade15FruDescriptionEntry 10 }
		
 		b15fruProductRevision OBJECT-TYPE
			SYNTAX DisplayString
			MAX-ACCESS read-only
			STATUS current
			DESCRIPTION
				"Used to read the Product Revision from the blade14 fru."
			::= { blade15FruDescriptionEntry 13 }
		
 		b15fruAll OBJECT-TYPE
			SYNTAX DisplayString
			MAX-ACCESS read-only
			STATUS current
			DESCRIPTION
				"Used to read the fru info all."
			::= { blade15FruDescriptionEntry 14 }
		
		blade15CPUTable OBJECT-TYPE
			SYNTAX SEQUENCE OF Blade15CPUEntry
			MAX-ACCESS not-accessible
			STATUS current
			DESCRIPTION
				"A table containing the list of Blade1 FRU information."
			::= { blade15 2006 }
		
		blade15CPUEntry OBJECT-TYPE
			SYNTAX Blade15CPUEntry
			MAX-ACCESS not-accessible
			STATUS current
			DESCRIPTION
				"Information about a particular current FRU."
			INDEX { b15CPUIndex }
			::= { blade15CPUTable 1 }
		
		Blade15CPUEntry ::=
			SEQUENCE { 
				b15CPUIndex
					INTEGER,
				b15CPUMark
					DisplayString,
				b15CPUInfo
					DisplayString,
				b15CPUPresent
					INTEGER,
				b15CPUHealth
					INTEGER,
				b15CPULocation
					DisplayString
			 }

		b15CPUIndex OBJECT-TYPE
			SYNTAX INTEGER
			MAX-ACCESS not-accessible
			STATUS current
			DESCRIPTION
				"CPU INDEX"
			::= { blade15CPUEntry 1 }
		
		b15CPUMark OBJECT-TYPE
			SYNTAX DisplayString
			MAX-ACCESS read-only
			STATUS current
			DESCRIPTION
				"Get the CPU silk-screen."
			::= { blade15CPUEntry 2 }
		
		b15CPUInfo OBJECT-TYPE
			SYNTAX DisplayString
			MAX-ACCESS read-only
			STATUS current
			DESCRIPTION
				"Get the CPU description of vendor, type and frequency."
			::= { blade15CPUEntry 3 }
		
		b15CPUPresent OBJECT-TYPE
			SYNTAX INTEGER
			MAX-ACCESS read-only
			STATUS current
			DESCRIPTION
				"Get the CPU presence status."
			::= { blade15CPUEntry 4 }
		
		b15CPUHealth OBJECT-TYPE
			SYNTAX INTEGER
			MAX-ACCESS read-only
			STATUS current
			DESCRIPTION
				"Get the CPU health status."
			::= { blade15CPUEntry 5 }
		
		b15CPULocation OBJECT-TYPE
			SYNTAX DisplayString
			MAX-ACCESS read-only
			STATUS current
			DESCRIPTION
				"Get the CPU location."
			::= { blade15CPUEntry 6 }
		
		blade15MemoryTable OBJECT-TYPE
			SYNTAX SEQUENCE OF Blade15MemoryEntry
			MAX-ACCESS not-accessible
			STATUS current
			DESCRIPTION
				"A table containing the list of Blade1 FRU information."
			::= { blade15 2007 }
		
		blade15MemoryEntry OBJECT-TYPE
			SYNTAX Blade15MemoryEntry
			MAX-ACCESS not-accessible
			STATUS current
			DESCRIPTION
				"Information about a particular current FRU."
			INDEX { b15MEMIndex }
			::= { blade15MemoryTable 1 }
		
		Blade15MemoryEntry ::=
			SEQUENCE { 
				b15MEMIndex
					INTEGER,
				b15MEMMark
					DisplayString,
				b15MEMInfo
					DisplayString,
				b15MEMPresent
					INTEGER,
				b15MEMHealth
					INTEGER,
				b15MEMLocation
					DisplayString
			 }

		b15MEMIndex OBJECT-TYPE
			SYNTAX INTEGER
			MAX-ACCESS not-accessible
			STATUS current
			DESCRIPTION
				"MEMORY INDEX"
			::= { blade15MemoryEntry 1 }
		
		b15MEMMark OBJECT-TYPE
			SYNTAX DisplayString
			MAX-ACCESS read-only
			STATUS current
			DESCRIPTION
				"Get the memory silk-screen."
			::= { blade15MemoryEntry 2 }
		
		b15MEMInfo OBJECT-TYPE
			SYNTAX DisplayString
			MAX-ACCESS read-only
			STATUS current
			DESCRIPTION
				"Get the memory description of vendor, frequency and capacity."
			::= { blade15MemoryEntry 3 }
		
		b15MEMPresent OBJECT-TYPE
			SYNTAX INTEGER
			MAX-ACCESS read-only
			STATUS current
			DESCRIPTION
				"Get the memory presence status."
			::= { blade15MemoryEntry 4 }
		
		b15MEMHealth OBJECT-TYPE
			SYNTAX INTEGER
			MAX-ACCESS read-only
			STATUS current
			DESCRIPTION
				"Get the memory health status."
			::= { blade15MemoryEntry 5 }
		
		b15MEMLocation OBJECT-TYPE
			SYNTAX DisplayString
			MAX-ACCESS read-only
			STATUS current
			DESCRIPTION
				"Get the memory location."
			::= { blade15MemoryEntry 6 }
		
		blade15MezzTable OBJECT-TYPE
			SYNTAX SEQUENCE OF Blade15MezzEntry
			MAX-ACCESS not-accessible
			STATUS current
			DESCRIPTION
				"A table containing the list of Blade1 FRU information."
			::= { blade15 2008 }
		
		blade15MezzEntry OBJECT-TYPE
			SYNTAX Blade15MezzEntry
			MAX-ACCESS not-accessible
			STATUS current
			DESCRIPTION
				"Information about a particular current FRU."
			INDEX { b15MezzIndex }
			::= { blade15MezzTable 1 }
		
		Blade15MezzEntry ::=
			SEQUENCE { 
				b15MezzIndex
					INTEGER,
				b15MezzMark
					DisplayString,
				b15MezzInfo
					DisplayString,
				b15MezzPresent
					INTEGER,
				b15MezzHealth
					INTEGER,
				b15MezzLocation
					DisplayString,
				b15MezzMac
					DisplayString
			 }

		b15MezzIndex OBJECT-TYPE
			SYNTAX INTEGER
			MAX-ACCESS not-accessible
			STATUS current
			DESCRIPTION
				"MEZZ INDEX"
			::= { blade15MezzEntry 1 }
		
		b15MezzMark OBJECT-TYPE
			SYNTAX DisplayString
			MAX-ACCESS read-only
			STATUS current
			DESCRIPTION
				"Get the MEZZ silk-screen."
			::= { blade15MezzEntry 2 }
		
		b15MezzInfo OBJECT-TYPE
			SYNTAX DisplayString
			MAX-ACCESS read-only
			STATUS current
			DESCRIPTION
				"Get the MEZZ description of type."
			::= { blade15MezzEntry 3 }
		
		b15MezzPresent OBJECT-TYPE
			SYNTAX INTEGER
			MAX-ACCESS read-only
			STATUS current
			DESCRIPTION
				"Get the MEZZ presence status."
			::= { blade15MezzEntry 4 }
		
		b15MezzHealth OBJECT-TYPE
			SYNTAX INTEGER
			MAX-ACCESS read-only
			STATUS current
			DESCRIPTION
				"Get the MEZZ health status."
			::= { blade15MezzEntry 5 }
		
		b15MezzLocation OBJECT-TYPE
			SYNTAX DisplayString
			MAX-ACCESS read-only
			STATUS current
			DESCRIPTION
				"Get the MEZZ location."
			::= { blade15MezzEntry 6 }
		
		b15MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade15MezzEntry 7 }
		
		blade15DiskTable OBJECT-TYPE
			SYNTAX SEQUENCE OF Blade15DiskEntry
			MAX-ACCESS not-accessible
			STATUS current
			DESCRIPTION
				"A table containing the list of Blade1 FRU information."
			::= { blade15 2009 }
		
		blade15DiskEntry OBJECT-TYPE
			SYNTAX Blade15DiskEntry
			MAX-ACCESS not-accessible
			STATUS current
			DESCRIPTION
				"Information about a particular current FRU."
			INDEX { b15DiskIndex }
			::= { blade15DiskTable 1 }
		
		Blade15DiskEntry ::=
			SEQUENCE { 
				b15DiskIndex
					INTEGER,
				b15DiskMark
					DisplayString,
				b15DiskInfo
					DisplayString,
				b15DiskPresent
					INTEGER,
				b15DiskHealth
					INTEGER,
				b15DiskLocation
					DisplayString
			 }

		b15DiskIndex OBJECT-TYPE
			SYNTAX INTEGER
			MAX-ACCESS not-accessible
			STATUS current
			DESCRIPTION
				"DISK INDEX"
			::= { blade15DiskEntry 1 }
		
		b15DiskMark OBJECT-TYPE
			SYNTAX DisplayString
			MAX-ACCESS read-only
			STATUS current
			DESCRIPTION
				"Get the disk silk-screen."
			::= { blade15DiskEntry 2 }
		
		b15DiskInfo OBJECT-TYPE
			SYNTAX DisplayString
			MAX-ACCESS read-only
			STATUS current
			DESCRIPTION
				"Get the disk description of vendor, capacity and speed."
			::= { blade15DiskEntry 3 }
		
		b15DiskPresent OBJECT-TYPE
			SYNTAX INTEGER
			MAX-ACCESS read-only
			STATUS current
			DESCRIPTION
				"Get the disk presence status."
			::= { blade15DiskEntry 4 }
		
		b15DiskHealth OBJECT-TYPE
			SYNTAX INTEGER
			MAX-ACCESS read-only
			STATUS current
			DESCRIPTION
				"Get the disk health status."
			::= { blade15DiskEntry 5 }
		
		b15DiskLocation OBJECT-TYPE
			SYNTAX DisplayString
			MAX-ACCESS read-only
			STATUS current
			DESCRIPTION
				"Get the disk location."
			::= { blade15DiskEntry 6 }
		
		blade15SecretKvmVmmTable OBJECT-TYPE
			SYNTAX SEQUENCE OF Blade15SecretKvmVmmEntry
			MAX-ACCESS not-accessible
			STATUS current
			DESCRIPTION
				"A table containing the list of Blade15 KVM&VMM secret information."
			::= { blade15 2010 }

		blade15SecretKvmVmmEntry OBJECT-TYPE
			SYNTAX Blade15SecretKvmVmmEntry
			MAX-ACCESS not-accessible
			STATUS current
			DESCRIPTION
				"Information about a particular current KVM&VMM."
			INDEX { b15SecretKvmVmmIndex }
			::= { blade15SecretKvmVmmTable 1 }
		Blade15SecretKvmVmmEntry ::=
			SEQUENCE { 
				b15SecretKvmVmmIndex
					INTEGER,
				b15SecretKvmState
					INTEGER,
				b15SecretVmmState
					INTEGER,
				b15MMSecretVmmKey
					DisplayString,
				b15SecretVmmKey
					DisplayString
			 }
		b15SecretKvmVmmIndex OBJECT-TYPE
			SYNTAX INTEGER
			MAX-ACCESS not-accessible
			STATUS current
			DESCRIPTION
				"KVM&VMM INDEX."
			::= { blade15SecretKvmVmmEntry 1 }
		b15SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade15SecretKvmVmmEntry 2 }
		b15SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade15SecretKvmVmmEntry 3 }
		b15MMSecretVmmKey OBJECT-TYPE
			SYNTAX DisplayString
			MAX-ACCESS read-only
			STATUS current
			DESCRIPTION
				"Get the MM secret VMM key."
			::= { blade15SecretKvmVmmEntry 4 }
		b15SecretVmmKey OBJECT-TYPE
			SYNTAX DisplayString
			MAX-ACCESS read-write
			STATUS current
			DESCRIPTION
				"Set the secret VMM key."
			::= { blade15SecretKvmVmmEntry 5 }
		blade16 OBJECT IDENTIFIER ::= { blades 16 }

		
 		b16DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade16 4 }
		
 		b16PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade16 5 }
		
 		b16Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade16 6 }

		
 		b16Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade16 8 }
		
 		b16HealthEvents OBJECT-TYPE
			SYNTAX DisplayString
			MAX-ACCESS read-only
			STATUS current
			DESCRIPTION
				"Events that contribute to the b14Health of the b14Location.  
				This is a list of events currently happening on the 
				b14Location."
			::= { blade16 9 }
		
 		b16ClearSEL OBJECT-TYPE
			SYNTAX INTEGER { clear(1) }
			MAX-ACCESS read-write
			STATUS current
			DESCRIPTION
				"Clean the BMC's SEL on the board."
			::= { blade16 12 }
		
 		b16ExDiskBoardPresence OBJECT-TYPE
			SYNTAX INTEGER
				{
				not-present(0),
				present(1)
				}
			MAX-ACCESS read-only
			STATUS current
			DESCRIPTION
				"Used to find out if the extended disk board is present.
				0 - not present
				1 - present"
			::= { blade16 14 }
		
 		b16BladeVersion OBJECT-TYPE
			SYNTAX DisplayString
			MAX-ACCESS read-only
			STATUS current
			DESCRIPTION
				"display the Version of board14."
			::= { blade16 20 }
		
 		b16MACAddress OBJECT-TYPE
			SYNTAX DisplayString
			MAX-ACCESS read-only
			STATUS current
			DESCRIPTION
				"display the MACAddress of board14."
			::= { blade16 21 }
		
				
							
		
 		b16Safepwofftime OBJECT-TYPE
			SYNTAX INTEGER
			MAX-ACCESS read-write
			STATUS current
			DESCRIPTION
				"the safe poweroff time.
				"
			::= { blade16 26 }
		
 		b16BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade16 32 }
		
 		b16Systeminfo OBJECT-TYPE
			SYNTAX DisplayString
			MAX-ACCESS read-write
			STATUS current
			DESCRIPTION
				"display the system information of board14."
			::= { blade16 36 }

		
 		b16SystemProperties OBJECT-TYPE
			SYNTAX DisplayString
			MAX-ACCESS read-only
			STATUS current
			DESCRIPTION
				"Get the power of blade1."
			::= { blade16 39 }
		
 		b16BiosCfg OBJECT-TYPE
			SYNTAX DisplayString
			MAX-ACCESS read-write
			STATUS current
			DESCRIPTION
				"Get the power of blade1."
			::= { blade16 40 }
		
 		b16WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade16 41 }
		
 		b16RealTimePower OBJECT-TYPE
			SYNTAX INTEGER
			MAX-ACCESS read-only
			STATUS current
			DESCRIPTION
				" "
			::= { blade16 43 }
		
 		b16PowerCapping OBJECT-TYPE
			SYNTAX DisplayString
			MAX-ACCESS read-write
			STATUS current
			DESCRIPTION
				" "
			::= { blade16 44 }
		
 		b16Powerreference OBJECT-TYPE
			SYNTAX INTEGER
			MAX-ACCESS read-only
			STATUS current
			DESCRIPTION
				" "
			::= { blade16 45 }
		
 		b16ClearBiosConfig OBJECT-TYPE
			SYNTAX INTEGER
			MAX-ACCESS read-write
			STATUS current
			DESCRIPTION
				" "
			::= { blade16 46 }
		
 		b16BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade16 47 }
		
 		b16BmcUserAdd OBJECT-TYPE
			SYNTAX DisplayString
			MAX-ACCESS read-write
			STATUS current
			DESCRIPTION
				"Used to Add the BMC User
				settable format:
				username,passwd"
			::= { blade16 48 }
		
 		b16BmcUserDel OBJECT-TYPE
			SYNTAX DisplayString
			MAX-ACCESS read-write
			STATUS current
			DESCRIPTION
				"Used to Del the BMC User
				settable format:
				username"
			::= { blade16 49 }
		
 		b16BmcUserPasswd OBJECT-TYPE
			SYNTAX DisplayString
			MAX-ACCESS read-write
			STATUS current
			DESCRIPTION
				"Used to Change the BMC User Passwd
				settable format:
				username,passwd"
			::= { blade16 50 }
		
 		b16BmcUserpropertychg OBJECT-TYPE
			SYNTAX DisplayString
			MAX-ACCESS read-write
			STATUS current
			DESCRIPTION
				"Used to Change the BMC User Property
				settable format:
				username,property"
			::= { blade16 51 }
		
 		b16BmcGateway OBJECT-TYPE
			SYNTAX DisplayString
			MAX-ACCESS read-write
			STATUS current
			DESCRIPTION
				"Read or set the gateway."
			::= { blade16 52 }
		
 		b16SlotBitmap OBJECT-TYPE
			SYNTAX INTEGER
			MAX-ACCESS read-only
			STATUS current
			DESCRIPTION
				" "
			::= { blade16 55 }
		
		b16systemGuid OBJECT-TYPE
			SYNTAX DisplayString
			MAX-ACCESS read-only
			STATUS current
			DESCRIPTION
				" "
			::= { blade16 56 }
		
		b16ProductName OBJECT-TYPE
			SYNTAX DisplayString
			MAX-ACCESS read-only
			STATUS current
			DESCRIPTION
				"display the Version of board14."
			::= { blade16 57 }
		
		b16BundleVersion OBJECT-TYPE
			SYNTAX DisplayString
			MAX-ACCESS read-write
			STATUS current
			DESCRIPTION
				"Get or set the board16 bundle version."
			::= { blade16 58 }

 		blade16SensorTargetTable OBJECT-TYPE
			SYNTAX SEQUENCE OF Blade16SensorTargetEntry
			MAX-ACCESS not-accessible
			STATUS current
			DESCRIPTION
				"A table containing the list of sensor information."
			::= { blade16 2001 }
		
 		blade16SensorTargetEntry OBJECT-TYPE
			SYNTAX Blade16SensorTargetEntry
			MAX-ACCESS not-accessible
			STATUS current
			DESCRIPTION
				"Information about a particular current sensor."
			INDEX { b16Target }
			::= { blade16SensorTargetTable 1 }
		
		Blade16SensorTargetEntry ::=
			SEQUENCE { 
				b16Target
					DisplayString,
				b16Current
					DisplayString,
				b16ThresholdsAll
					DisplayString,
				b16UpperCritical
					DisplayString,
				b16UpperNonCritical
					DisplayString,
				b16UpperNonRecoverable
					DisplayString,
				b16LowerNonCritical
					DisplayString,
				b16LowerCritical
					DisplayString,
				b16LowerNonRecoverable
					DisplayString,
				b16SensorHealth
					INTEGER,
				b16SensorHealthEvents
					DisplayString,
				b16NegativeHysteresis
					DisplayString,
				b16PositiveHysteresis
					DisplayString,
				b16SensorType
					DisplayString,
				b16SensorFRUInfo
					DisplayString
			 }

 		b16Target OBJECT-TYPE
			SYNTAX DisplayString
			MAX-ACCESS not-accessible
			STATUS current
			DESCRIPTION
				"sensor Name"
			::= { blade16SensorTargetEntry 1 }
		
 		b16Current OBJECT-TYPE
			SYNTAX DisplayString
			MAX-ACCESS read-only
			STATUS current
			DESCRIPTION
				"Display the current value of a sensor."
			::= { blade16SensorTargetEntry 2 }
		
 		b16ThresholdsAll OBJECT-TYPE
			SYNTAX DisplayString
			MAX-ACCESS read-only
			STATUS current
			DESCRIPTION
				"All thresholds of a sensor"
			::= { blade16SensorTargetEntry 3 }
		
 		b16UpperCritical OBJECT-TYPE
			SYNTAX DisplayString
			MAX-ACCESS read-write
			STATUS current
			DESCRIPTION
				"Upper critical thresholds"
			::= { blade16SensorTargetEntry 4 }
		
 		b16UpperNonCritical OBJECT-TYPE
			SYNTAX DisplayString
			MAX-ACCESS read-write
			STATUS current
			DESCRIPTION
				"Upper non-critical thresholds"
			::= { blade16SensorTargetEntry 5 }
		
 		b16UpperNonRecoverable OBJECT-TYPE
			SYNTAX DisplayString
			MAX-ACCESS read-write
			STATUS current
			DESCRIPTION
				"Upper non-recoverable thresholds"
			::= { blade16SensorTargetEntry 6 }
		
 		b16LowerNonCritical OBJECT-TYPE
			SYNTAX DisplayString
			MAX-ACCESS read-write
			STATUS current
			DESCRIPTION
				"Lower non-critical thresholds"
			::= { blade16SensorTargetEntry 7 }
		
 		b16LowerCritical OBJECT-TYPE
			SYNTAX DisplayString
			MAX-ACCESS read-write
			STATUS current
			DESCRIPTION
				"Lower critical thresholds"
			::= { blade16SensorTargetEntry 8 }
		
 		b16LowerNonRecoverable OBJECT-TYPE
			SYNTAX DisplayString
			MAX-ACCESS read-write
			STATUS current
			DESCRIPTION
				"Lower non-recoverable thresholds"
			::= { blade16SensorTargetEntry 9 }
		
 		b16SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade16SensorTargetEntry 10 }
		
 		b16SensorHealthEvents OBJECT-TYPE
			SYNTAX DisplayString
			MAX-ACCESS read-only
			STATUS current
			DESCRIPTION
				"Events that contribute to the b14Health of the b14Location.  
				This is a list of events currently happening on the 
				b14Location."
			::= { blade16SensorTargetEntry 11 }
		
		
 		b16NegativeHysteresis OBJECT-TYPE
			SYNTAX DisplayString
			MAX-ACCESS read-write
			STATUS current
			DESCRIPTION
				"Get/Set the negativeHysteresis value"
			::= { blade16SensorTargetEntry 16 }
		
 		b16PositiveHysteresis OBJECT-TYPE
			SYNTAX DisplayString
			MAX-ACCESS read-write
			STATUS current
			DESCRIPTION
				"Get/Set the positiveHysteresis value."
			::= { blade16SensorTargetEntry 17 }
		
 		b16SensorType OBJECT-TYPE
			SYNTAX DisplayString
			MAX-ACCESS read-only
			STATUS current
			DESCRIPTION
				"Get the type of the sensor."
			::= { blade16SensorTargetEntry 18 }
		
 		b16SensorFRUInfo OBJECT-TYPE
			SYNTAX DisplayString
			MAX-ACCESS read-only
			STATUS current
			DESCRIPTION
				"Get the fruinfo of the sensor."
			::= { blade16SensorTargetEntry 19 }
		
 		blade16FruTable OBJECT-TYPE
			SYNTAX SEQUENCE OF Blade16FruEntry
			MAX-ACCESS not-accessible
			STATUS current
			DESCRIPTION
				"A table containing the list of FRU information."
			::= { blade16 2002 }
		
 		blade16FruEntry OBJECT-TYPE
			SYNTAX Blade16FruEntry
			MAX-ACCESS not-accessible
			STATUS current
			DESCRIPTION
				"Information about a particular current FRU."
			INDEX { b16fruNumber }
			::= { blade16FruTable 1 }
		
		Blade16FruEntry ::=
			SEQUENCE { 
				b16fruNumber
					INTEGER,
				b16FruHotSwapState
					DisplayString,
				b16FruLedProperties
					DisplayString,
				b16FRUControl
					INTEGER,
				b16FRULabel
					DisplayString,
				b16ResetReason
					DisplayString
			 }

 		b16fruNumber OBJECT-TYPE
			SYNTAX INTEGER
			MAX-ACCESS not-accessible
			STATUS current
			DESCRIPTION
				" "
			::= { blade16FruEntry 1 }
		
 		b16FruHotSwapState OBJECT-TYPE
			SYNTAX DisplayString
			MAX-ACCESS read-only
			STATUS current
			DESCRIPTION
				"Retrieve the hot swap state of the FRU from the 
				internally known hot swap states of blade14."
			::= { blade16FruEntry 3 }
		
 		b16FruLedProperties OBJECT-TYPE
			SYNTAX DisplayString
			MAX-ACCESS read-only
			STATUS current
			DESCRIPTION
				"Retrieves the LED support information from a FRU. Returns a comma separated
				list of LEDS and the number of FRU supported user LEDs."
			::= { blade16FruEntry 4 }

		

		b16FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade16FruEntry 9 }
		
 		b16FRULabel OBJECT-TYPE
			SYNTAX DisplayString
			MAX-ACCESS read-only
			STATUS current
			DESCRIPTION
				"Get fru label of blade14."
			::= { blade16FruEntry 10 }
		
 		b16ResetReason OBJECT-TYPE
			SYNTAX DisplayString
			MAX-ACCESS read-only
			STATUS current
			DESCRIPTION
				"Delete fru label of smm."
			::= { blade16FruEntry 11 }
		
 		blade16FruLedTable OBJECT-TYPE
			SYNTAX SEQUENCE OF Blade16FruLedEntry
			MAX-ACCESS not-accessible
			STATUS current
			DESCRIPTION
				"A table containing the list of led information."
			::= { blade16 2003 }
		
 		blade16FruLedEntry OBJECT-TYPE
			SYNTAX Blade16FruLedEntry
			MAX-ACCESS not-accessible
			STATUS current
			DESCRIPTION
				"Information about a particular current led."
			INDEX { b16FruID, b16FruLed }
			::= { blade16FruLedTable 1 }
		
		Blade16FruLedEntry ::=
			SEQUENCE { 
				b16FruID
					INTEGER,
				b16FruLed
					DisplayString,
				b16FruLedColorProps
					DisplayString,
				b16FruLedState
					DisplayString
			 }

 		b16FruID OBJECT-TYPE
			SYNTAX INTEGER
			MAX-ACCESS not-accessible
			STATUS current
			DESCRIPTION
				" "
			::= { blade16FruLedEntry 1 }
		
 		b16FruLed OBJECT-TYPE
			SYNTAX DisplayString
			MAX-ACCESS not-accessible
			STATUS current
			DESCRIPTION
				" "
			::= { blade16FruLedEntry 2 }
		
 		b16FruLedColorProps OBJECT-TYPE
			SYNTAX DisplayString
			MAX-ACCESS read-only
			STATUS current
			DESCRIPTION
				"Finds out what colors are supported by the LED"
			::= { blade16FruLedEntry 3 }
		
 		b16FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade16FruLedEntry 4 }
		
 		blade16FruDescriptionTable OBJECT-TYPE
			SYNTAX SEQUENCE OF Blade16FruDescriptionEntry
			MAX-ACCESS not-accessible
			STATUS current
			DESCRIPTION
				"A table containing the list of blade14 FRU information."
			::= { blade16 2004 }
		
 		blade16FruDescriptionEntry OBJECT-TYPE
			SYNTAX Blade16FruDescriptionEntry
			MAX-ACCESS not-accessible
			STATUS current
			DESCRIPTION
				"Information about a particular current FRU."
			INDEX { b16fruNum }
			::= { blade16FruDescriptionTable 1 }
		
		Blade16FruDescriptionEntry ::=
			SEQUENCE { 
				b16fruNum
					INTEGER,
				b16fruBoardDescription
					DisplayString,
				b16fruBoardManufacturer
					DisplayString,
				b16fruBoardPartNumber
					DisplayString,
				b16fruBoardSerialNumber
					DisplayString,
				b16fruBoardManufactureDate
					DisplayString,
				b16fruProductDescription
					DisplayString,
				b16fruProductManufacturer
					DisplayString,
				b16fruProductPartNumber
					DisplayString,
				b16fruProductSerialNumber
					DisplayString,
				b16fruProductRevision
					DisplayString,
				b16fruAll
					DisplayString
			 }

 		b16fruNum OBJECT-TYPE
			SYNTAX INTEGER
			MAX-ACCESS not-accessible
			STATUS current
			DESCRIPTION
				"blade14 FRU's INDEX"
			::= { blade16FruDescriptionEntry 1 }
		
 		b16fruBoardDescription OBJECT-TYPE
			SYNTAX DisplayString
			MAX-ACCESS read-only
			STATUS current
			DESCRIPTION
				"Used to read the Board Description from the blade14 fru."
			::= { blade16FruDescriptionEntry 2 }
		
 		b16fruBoardManufacturer OBJECT-TYPE
			SYNTAX DisplayString
			MAX-ACCESS read-only
			STATUS current
			DESCRIPTION
				"Used to read the Board Manufacturer from the bladef14 fru."
			::= { blade16FruDescriptionEntry 3 }
		
 		b16fruBoardPartNumber OBJECT-TYPE
			SYNTAX DisplayString
			MAX-ACCESS read-only
			STATUS current
			DESCRIPTION
				"Used to read the Board Part Number from the blade14 fru."
			::= { blade16FruDescriptionEntry 4 }
		
 		b16fruBoardSerialNumber OBJECT-TYPE
			SYNTAX DisplayString
			MAX-ACCESS read-only
			STATUS current
			DESCRIPTION
				"Used to read the Board Serial Number from the blade14 fru."
			::= { blade16FruDescriptionEntry 5 }
		
 		b16fruBoardManufactureDate OBJECT-TYPE
			SYNTAX DisplayString
			MAX-ACCESS read-only
			STATUS current
			DESCRIPTION
				"Used to read the Board Manufacture Date from the blade14 fru."
			::= { blade16FruDescriptionEntry 6 }
		
 		b16fruProductDescription OBJECT-TYPE
			SYNTAX DisplayString
			MAX-ACCESS read-only
			STATUS current
			DESCRIPTION
				"Used to read the Product Description from the blade14 fru."
			::= { blade16FruDescriptionEntry 7 }
		
 		b16fruProductManufacturer OBJECT-TYPE
			SYNTAX DisplayString
			MAX-ACCESS read-only
			STATUS current
			DESCRIPTION
				"Used to read the Product Manufacturer from the blade14 fru."
			::= { blade16FruDescriptionEntry 8 }
		
 		b16fruProductPartNumber OBJECT-TYPE
			SYNTAX DisplayString
			MAX-ACCESS read-only
			STATUS current
			DESCRIPTION
				"Used to read the Product Part Number from the blade14 fru."
			::= { blade16FruDescriptionEntry 9 }
		
 		b16fruProductSerialNumber OBJECT-TYPE
			SYNTAX DisplayString
			MAX-ACCESS read-only
			STATUS current
			DESCRIPTION
				"Used to read the Product Serial Number from the blade14 fru."
			::= { blade16FruDescriptionEntry 10 }
		
 		b16fruProductRevision OBJECT-TYPE
			SYNTAX DisplayString
			MAX-ACCESS read-only
			STATUS current
			DESCRIPTION
				"Used to read the Product Revision from the blade14 fru."
			::= { blade16FruDescriptionEntry 13 }
		
 		b16fruAll OBJECT-TYPE
			SYNTAX DisplayString
			MAX-ACCESS read-only
			STATUS current
			DESCRIPTION
				"Used to read the fru info all."
			::= { blade16FruDescriptionEntry 14 }
		
		blade16CPUTable OBJECT-TYPE
			SYNTAX SEQUENCE OF Blade16CPUEntry
			MAX-ACCESS not-accessible
			STATUS current
			DESCRIPTION
				"A table containing the list of Blade1 FRU information."
			::= { blade16 2006 }
		
		blade16CPUEntry OBJECT-TYPE
			SYNTAX Blade16CPUEntry
			MAX-ACCESS not-accessible
			STATUS current
			DESCRIPTION
				"Information about a particular current FRU."
			INDEX { b16CPUIndex }
			::= { blade16CPUTable 1 }
		
		Blade16CPUEntry ::=
			SEQUENCE { 
				b16CPUIndex
					INTEGER,
				b16CPUMark
					DisplayString,
				b16CPUInfo
					DisplayString,
				b16CPUPresent
					INTEGER,
				b16CPUHealth
					INTEGER,
				b16CPULocation
					DisplayString
			 }

		b16CPUIndex OBJECT-TYPE
			SYNTAX INTEGER
			MAX-ACCESS not-accessible
			STATUS current
			DESCRIPTION
				"CPU INDEX"
			::= { blade16CPUEntry 1 }
		
		b16CPUMark OBJECT-TYPE
			SYNTAX DisplayString
			MAX-ACCESS read-only
			STATUS current
			DESCRIPTION
				"Get the CPU silk-screen."
			::= { blade16CPUEntry 2 }
		
		b16CPUInfo OBJECT-TYPE
			SYNTAX DisplayString
			MAX-ACCESS read-only
			STATUS current
			DESCRIPTION
				"Get the CPU description of vendor, type and frequency."
			::= { blade16CPUEntry 3 }
		
		b16CPUPresent OBJECT-TYPE
			SYNTAX INTEGER
			MAX-ACCESS read-only
			STATUS current
			DESCRIPTION
				"Get the CPU presence status."
			::= { blade16CPUEntry 4 }
		
		b16CPUHealth OBJECT-TYPE
			SYNTAX INTEGER
			MAX-ACCESS read-only
			STATUS current
			DESCRIPTION
				"Get the CPU health status."
			::= { blade16CPUEntry 5 }
		
		b16CPULocation OBJECT-TYPE
			SYNTAX DisplayString
			MAX-ACCESS read-only
			STATUS current
			DESCRIPTION
				"Get the CPU location."
			::= { blade16CPUEntry 6 }
		
		blade16MemoryTable OBJECT-TYPE
			SYNTAX SEQUENCE OF Blade16MemoryEntry
			MAX-ACCESS not-accessible
			STATUS current
			DESCRIPTION
				"A table containing the list of Blade1 FRU information."
			::= { blade16 2007 }
		
		blade16MemoryEntry OBJECT-TYPE
			SYNTAX Blade16MemoryEntry
			MAX-ACCESS not-accessible
			STATUS current
			DESCRIPTION
				"Information about a particular current FRU."
			INDEX { b16MEMIndex }
			::= { blade16MemoryTable 1 }
		
		Blade16MemoryEntry ::=
			SEQUENCE { 
				b16MEMIndex
					INTEGER,
				b16MEMMark
					DisplayString,
				b16MEMInfo
					DisplayString,
				b16MEMPresent
					INTEGER,
				b16MEMHealth
					INTEGER,
				b16MEMLocation
					DisplayString
			 }

		b16MEMIndex OBJECT-TYPE
			SYNTAX INTEGER
			MAX-ACCESS not-accessible
			STATUS current
			DESCRIPTION
				"MEMORY INDEX"
			::= { blade16MemoryEntry 1 }
		
		b16MEMMark OBJECT-TYPE
			SYNTAX DisplayString
			MAX-ACCESS read-only
			STATUS current
			DESCRIPTION
				"Get the memory silk-screen."
			::= { blade16MemoryEntry 2 }
		
		b16MEMInfo OBJECT-TYPE
			SYNTAX DisplayString
			MAX-ACCESS read-only
			STATUS current
			DESCRIPTION
				"Get the memory description of vendor, frequency and capacity."
			::= { blade16MemoryEntry 3 }
		
		b16MEMPresent OBJECT-TYPE
			SYNTAX INTEGER
			MAX-ACCESS read-only
			STATUS current
			DESCRIPTION
				"Get the memory presence status."
			::= { blade16MemoryEntry 4 }
		
		b16MEMHealth OBJECT-TYPE
			SYNTAX INTEGER
			MAX-ACCESS read-only
			STATUS current
			DESCRIPTION
				"Get the memory health status."
			::= { blade16MemoryEntry 5 }
		
		b16MEMLocation OBJECT-TYPE
			SYNTAX DisplayString
			MAX-ACCESS read-only
			STATUS current
			DESCRIPTION
				"Get the memory location."
			::= { blade16MemoryEntry 6 }
		
		blade16MezzTable OBJECT-TYPE
			SYNTAX SEQUENCE OF Blade16MezzEntry
			MAX-ACCESS not-accessible
			STATUS current
			DESCRIPTION
				"A table containing the list of Blade1 FRU information."
			::= { blade16 2008 }
		
		blade16MezzEntry OBJECT-TYPE
			SYNTAX Blade16MezzEntry
			MAX-ACCESS not-accessible
			STATUS current
			DESCRIPTION
				"Information about a particular current FRU."
			INDEX { b16MezzIndex }
			::= { blade16MezzTable 1 }
		
		Blade16MezzEntry ::=
			SEQUENCE { 
				b16MezzIndex
					INTEGER,
				b16MezzMark
					DisplayString,
				b16MezzInfo
					DisplayString,
				b16MezzPresent
					INTEGER,
				b16MezzHealth
					INTEGER,
				b16MezzLocation
					DisplayString,
				b16MezzMac
					DisplayString
			 }

		b16MezzIndex OBJECT-TYPE
			SYNTAX INTEGER
			MAX-ACCESS not-accessible
			STATUS current
			DESCRIPTION
				"MEZZ INDEX"
			::= { blade16MezzEntry 1 }
		
		b16MezzMark OBJECT-TYPE
			SYNTAX DisplayString
			MAX-ACCESS read-only
			STATUS current
			DESCRIPTION
				"Get the MEZZ silk-screen."
			::= { blade16MezzEntry 2 }
		
		b16MezzInfo OBJECT-TYPE
			SYNTAX DisplayString
			MAX-ACCESS read-only
			STATUS current
			DESCRIPTION
				"Get the MEZZ description of type."
			::= { blade16MezzEntry 3 }
		
		b16MezzPresent OBJECT-TYPE
			SYNTAX INTEGER
			MAX-ACCESS read-only
			STATUS current
			DESCRIPTION
				"Get the MEZZ presence status."
			::= { blade16MezzEntry 4 }
		
		b16MezzHealth OBJECT-TYPE
			SYNTAX INTEGER
			MAX-ACCESS read-only
			STATUS current
			DESCRIPTION
				"Get the MEZZ health status."
			::= { blade16MezzEntry 5 }
		
		b16MezzLocation OBJECT-TYPE
			SYNTAX DisplayString
			MAX-ACCESS read-only
			STATUS current
			DESCRIPTION
				"Get the MEZZ location."
			::= { blade16MezzEntry 6 }
		
		b16MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade16MezzEntry 7 }
		
		blade16DiskTable OBJECT-TYPE
			SYNTAX SEQUENCE OF Blade16DiskEntry
			MAX-ACCESS not-accessible
			STATUS current
			DESCRIPTION
				"A table containing the list of Blade1 FRU information."
			::= { blade16 2009 }
		
		blade16DiskEntry OBJECT-TYPE
			SYNTAX Blade16DiskEntry
			MAX-ACCESS not-accessible
			STATUS current
			DESCRIPTION
				"Information about a particular current FRU."
			INDEX { b16DiskIndex }
			::= { blade16DiskTable 1 }
		
		Blade16DiskEntry ::=
			SEQUENCE { 
				b16DiskIndex
					INTEGER,
				b16DiskMark
					DisplayString,
				b16DiskInfo
					DisplayString,
				b16DiskPresent
					INTEGER,
				b16DiskHealth
					INTEGER,
				b16DiskLocation
					DisplayString
			 }

		b16DiskIndex OBJECT-TYPE
			SYNTAX INTEGER
			MAX-ACCESS not-accessible
			STATUS current
			DESCRIPTION
				"DISK INDEX"
			::= { blade16DiskEntry 1 }
		
		b16DiskMark OBJECT-TYPE
			SYNTAX DisplayString
			MAX-ACCESS read-only
			STATUS current
			DESCRIPTION
				"Get the disk silk-screen."
			::= { blade16DiskEntry 2 }
		
		b16DiskInfo OBJECT-TYPE
			SYNTAX DisplayString
			MAX-ACCESS read-only
			STATUS current
			DESCRIPTION
				"Get the disk description of vendor, capacity and speed."
			::= { blade16DiskEntry 3 }
		
		b16DiskPresent OBJECT-TYPE
			SYNTAX INTEGER
			MAX-ACCESS read-only
			STATUS current
			DESCRIPTION
				"Get the disk presence status."
			::= { blade16DiskEntry 4 }
		
		b16DiskHealth OBJECT-TYPE
			SYNTAX INTEGER
			MAX-ACCESS read-only
			STATUS current
			DESCRIPTION
				"Get the disk health status."
			::= { blade16DiskEntry 5 }
		
		b16DiskLocation OBJECT-TYPE
			SYNTAX DisplayString
			MAX-ACCESS read-only
			STATUS current
			DESCRIPTION
				"Get the disk location."
			::= { blade16DiskEntry 6 }
		
		blade16SecretKvmVmmTable OBJECT-TYPE
			SYNTAX SEQUENCE OF Blade16SecretKvmVmmEntry
			MAX-ACCESS not-accessible
			STATUS current
			DESCRIPTION
				"A table containing the list of Blade16 KVM&VMM secret information."
			::= { blade16 2010 }

		blade16SecretKvmVmmEntry OBJECT-TYPE
			SYNTAX Blade16SecretKvmVmmEntry
			MAX-ACCESS not-accessible
			STATUS current
			DESCRIPTION
				"Information about a particular current KVM&VMM."
			INDEX { b16SecretKvmVmmIndex }
			::= { blade16SecretKvmVmmTable 1 }
		Blade16SecretKvmVmmEntry ::=
			SEQUENCE { 
				b16SecretKvmVmmIndex
					INTEGER,
				b16SecretKvmState
					INTEGER,
				b16SecretVmmState
					INTEGER,
				b16MMSecretVmmKey
					DisplayString,
				b16SecretVmmKey
					DisplayString
			 }
		b16SecretKvmVmmIndex OBJECT-TYPE
			SYNTAX INTEGER
			MAX-ACCESS not-accessible
			STATUS current
			DESCRIPTION
				"KVM&VMM INDEX."
			::= { blade16SecretKvmVmmEntry 1 }
		b16SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade16SecretKvmVmmEntry 2 }
		b16SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade16SecretKvmVmmEntry 3 }
		b16MMSecretVmmKey OBJECT-TYPE
			SYNTAX DisplayString
			MAX-ACCESS read-only
			STATUS current
			DESCRIPTION
				"Get the MM secret VMM key."
			::= { blade16SecretKvmVmmEntry 4 }
		b16SecretVmmKey OBJECT-TYPE
			SYNTAX DisplayString
			MAX-ACCESS read-write
			STATUS current
			DESCRIPTION
				"Set the secret VMM key."
			::= { blade16SecretKvmVmmEntry 5 }
		blade17 OBJECT IDENTIFIER ::= { blades 17 }

		
 		b17DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade17 4 }
		
 		b17PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade17 5 }
		
 		b17Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade17 6 }

		
 		b17Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade17 8 }
		
 		b17HealthEvents OBJECT-TYPE
			SYNTAX DisplayString
			MAX-ACCESS read-only
			STATUS current
			DESCRIPTION
				"Events that contribute to the b1Health of the b1Location.  
				This is a list of events currently happening on the 
				b1Location."
			::= { blade17 9 }
		
 		b17ClearSEL OBJECT-TYPE
			SYNTAX INTEGER { clear(1) }
			MAX-ACCESS read-write
			STATUS current
			DESCRIPTION
				"Clean the BMC's SEL on the board."
			::= { blade17 12 }
		
 		b17ExDiskBoardPresence OBJECT-TYPE
			SYNTAX INTEGER
				{
				not-present(0),
				present(1)
				}
			MAX-ACCESS read-only
			STATUS current
			DESCRIPTION
				"Used to find out if the extended disk board is present.
				0 - not present
				1 - present"
			::= { blade17 14 }
		
 		b17BladeVersion OBJECT-TYPE
			SYNTAX DisplayString
			MAX-ACCESS read-only
			STATUS current
			DESCRIPTION
				"display the Version of board1."
			::= { blade17 20 }
		
 		b17MACAddress OBJECT-TYPE
			SYNTAX DisplayString
			MAX-ACCESS read-only
			STATUS current
			DESCRIPTION
				"display the MACAddress of board1."
			::= { blade17 21 }
		
				
							
		
 		b17Safepwofftime OBJECT-TYPE
			SYNTAX INTEGER
			MAX-ACCESS read-write
			STATUS current
			DESCRIPTION
				"the safe poweroff time.
				"
			::= { blade17 26 }
		
 		b17BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade17 32 }
		
 		b17Systeminfo OBJECT-TYPE
			SYNTAX DisplayString
			MAX-ACCESS read-write
			STATUS current
			DESCRIPTION
				"display the system information of board1."
			::= { blade17 36 }

		
 		b17SystemProperties OBJECT-TYPE
			SYNTAX DisplayString
			MAX-ACCESS read-only
			STATUS current
			DESCRIPTION
				"Get the power of blade1."
			::= { blade17 39 }
		
 		b17BiosCfg OBJECT-TYPE
			SYNTAX DisplayString
			MAX-ACCESS read-write
			STATUS current
			DESCRIPTION
				"Get the power of blade1."
			::= { blade17 40 }
		
 		b17WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade17 41 }
		
 		b17RealTimePower OBJECT-TYPE
			SYNTAX INTEGER
			MAX-ACCESS read-only
			STATUS current
			DESCRIPTION
				" "
			::= { blade17 43 }
		
 		b17PowerCapping OBJECT-TYPE
			SYNTAX DisplayString
			MAX-ACCESS read-write
			STATUS current
			DESCRIPTION
				" "
			::= { blade17 44 }
		
 		b17Powerreference OBJECT-TYPE
			SYNTAX INTEGER
			MAX-ACCESS read-only
			STATUS current
			DESCRIPTION
				" "
			::= { blade17 45 }
		
 		b17ClearBiosConfig OBJECT-TYPE
			SYNTAX INTEGER
			MAX-ACCESS read-write
			STATUS current
			DESCRIPTION
				" "
			::= { blade17 46 }
		
 		b17BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade17 47 }
		
 		b17BmcUserAdd OBJECT-TYPE
			SYNTAX DisplayString
			MAX-ACCESS read-write
			STATUS current
			DESCRIPTION
				"Used to Add the BMC User
				settable format:
				username,passwd"
			::= { blade17 48 }
		
 		b17BmcUserDel OBJECT-TYPE
			SYNTAX DisplayString
			MAX-ACCESS read-write
			STATUS current
			DESCRIPTION
				"Used to Del the BMC User
				settable format:
				username"
			::= { blade17 49 }
		
 		b17BmcUserPasswd OBJECT-TYPE
			SYNTAX DisplayString
			MAX-ACCESS read-write
			STATUS current
			DESCRIPTION
				"Used to Change the BMC User Passwd
				settable format:
				username,passwd"
			::= { blade17 50 }
		
 		b17BmcUserpropertychg OBJECT-TYPE
			SYNTAX DisplayString
			MAX-ACCESS read-write
			STATUS current
			DESCRIPTION
				"Used to Change the BMC User Property
				settable format:
				username,property"
			::= { blade17 51 }
		
 		b17BmcGateway OBJECT-TYPE
			SYNTAX DisplayString
			MAX-ACCESS read-write
			STATUS current
			DESCRIPTION
				"Read or set the gateway."
			::= { blade17 52 }
		
 		b17SlotBitmap OBJECT-TYPE
			SYNTAX INTEGER
			MAX-ACCESS read-only
			STATUS current
			DESCRIPTION
				" "
			::= { blade17 55 }
		
		b17systemGuid OBJECT-TYPE
			SYNTAX DisplayString
			MAX-ACCESS read-only
			STATUS current
			DESCRIPTION
				" "
			::= { blade17 56 }
		
		b17ProductName OBJECT-TYPE
			SYNTAX DisplayString
			MAX-ACCESS read-only
			STATUS current
			DESCRIPTION
				"display the Version of board1."
			::= { blade17 57 }
		
		b17BundleVersion OBJECT-TYPE
			SYNTAX DisplayString
			MAX-ACCESS read-write
			STATUS current
			DESCRIPTION
				"Get or set the board17 bundle version."
			::= { blade17 58 }

 		blade17SensorTargetTable OBJECT-TYPE
			SYNTAX SEQUENCE OF Blade17SensorTargetEntry
			MAX-ACCESS not-accessible
			STATUS current
			DESCRIPTION
				"A table containing the list of sensor information."
			::= { blade17 2001 }
		
 		blade17SensorTargetEntry OBJECT-TYPE
			SYNTAX Blade17SensorTargetEntry
			MAX-ACCESS not-accessible
			STATUS current
			DESCRIPTION
				"Information about a particular current sensor."
			INDEX { b1Target }
			::= { blade17SensorTargetTable 1 }
		
		Blade17SensorTargetEntry ::=
			SEQUENCE { 
				b17Target
					DisplayString,
				b17Current
					DisplayString,
				b17ThresholdsAll
					DisplayString,
				b17UpperCritical
					DisplayString,
				b17UpperNonCritical
					DisplayString,
				b17UpperNonRecoverable
					DisplayString,
				b17LowerNonCritical
					DisplayString,
				b17LowerCritical
					DisplayString,
				b17LowerNonRecoverable
					DisplayString,
				b17SensorHealth
					INTEGER,
				b17SensorHealthEvents
					DisplayString,
				b17NegativeHysteresis
					DisplayString,
				b17PositiveHysteresis
					DisplayString,
				b17SensorType
					DisplayString,
				b17SensorFRUInfo
					DisplayString
			 }

 		b17Target OBJECT-TYPE
			SYNTAX DisplayString
			MAX-ACCESS not-accessible
			STATUS current
			DESCRIPTION
				"sensor Name"
			::= { blade17SensorTargetEntry 1 }
		
 		b17Current OBJECT-TYPE
			SYNTAX DisplayString
			MAX-ACCESS read-only
			STATUS current
			DESCRIPTION
				"Display the current value of a sensor."
			::= { blade17SensorTargetEntry 2 }
		
 		b17ThresholdsAll OBJECT-TYPE
			SYNTAX DisplayString
			MAX-ACCESS read-only
			STATUS current
			DESCRIPTION
				"All thresholds of a sensor"
			::= { blade17SensorTargetEntry 3 }
		
 		b17UpperCritical OBJECT-TYPE
			SYNTAX DisplayString
			MAX-ACCESS read-write
			STATUS current
			DESCRIPTION
				"Upper critical thresholds"
			::= { blade17SensorTargetEntry 4 }
		
 		b17UpperNonCritical OBJECT-TYPE
			SYNTAX DisplayString
			MAX-ACCESS read-write
			STATUS current
			DESCRIPTION
				"Upper non-critical thresholds"
			::= { blade17SensorTargetEntry 5 }
		
 		b17UpperNonRecoverable OBJECT-TYPE
			SYNTAX DisplayString
			MAX-ACCESS read-write
			STATUS current
			DESCRIPTION
				"Upper non-recoverable thresholds"
			::= { blade17SensorTargetEntry 6 }
		
 		b17LowerNonCritical OBJECT-TYPE
			SYNTAX DisplayString
			MAX-ACCESS read-write
			STATUS current
			DESCRIPTION
				"Lower non-critical thresholds"
			::= { blade17SensorTargetEntry 7 }
		
 		b17LowerCritical OBJECT-TYPE
			SYNTAX DisplayString
			MAX-ACCESS read-write
			STATUS current
			DESCRIPTION
				"Lower critical thresholds"
			::= { blade17SensorTargetEntry 8 }
		
 		b17LowerNonRecoverable OBJECT-TYPE
			SYNTAX DisplayString
			MAX-ACCESS read-write
			STATUS current
			DESCRIPTION
				"Lower non-recoverable thresholds"
			::= { blade17SensorTargetEntry 9 }
		
 		b17SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade17SensorTargetEntry 10 }
		
 		b17SensorHealthEvents OBJECT-TYPE
			SYNTAX DisplayString
			MAX-ACCESS read-only
			STATUS current
			DESCRIPTION
				"Events that contribute to the b1Health of the b1Location.  
				This is a list of events currently happening on the 
				b1Location."
			::= { blade17SensorTargetEntry 11 }
		
		
 		b17NegativeHysteresis OBJECT-TYPE
			SYNTAX DisplayString
			MAX-ACCESS read-write
			STATUS current
			DESCRIPTION
				"Get/Set the negativeHysteresis value."
			::= { blade17SensorTargetEntry 16 }
		
 		b17PositiveHysteresis OBJECT-TYPE
			SYNTAX DisplayString
			MAX-ACCESS read-write
			STATUS current
			DESCRIPTION
				"Get/Set the positiveHysteresis value."
			::= { blade17SensorTargetEntry 17 }
		
 		b17SensorType OBJECT-TYPE
			SYNTAX DisplayString
			MAX-ACCESS read-only
			STATUS current
			DESCRIPTION
				"Get the type of the sensor."
			::= { blade17SensorTargetEntry 18 }
		
 		b17SensorFRUInfo OBJECT-TYPE
			SYNTAX DisplayString
			MAX-ACCESS read-only
			STATUS current
			DESCRIPTION
				"Get the fruinfo of the sensor."
			::= { blade17SensorTargetEntry 19 }
		
 		blade17FruTable OBJECT-TYPE
			SYNTAX SEQUENCE OF Blade17FruEntry
			MAX-ACCESS not-accessible
			STATUS current
			DESCRIPTION
				"A table containing the list of FRU information."
			::= { blade17 2002 }
		
 		blade17FruEntry OBJECT-TYPE
			SYNTAX Blade17FruEntry
			MAX-ACCESS not-accessible
			STATUS current
			DESCRIPTION
				"Information about a particular current FRU."
			INDEX { b1fruNumber }
			::= { blade17FruTable 1 }
		
		Blade17FruEntry ::=
			SEQUENCE { 
				b17fruNumber
					INTEGER,
				b17FruHotSwapState
					DisplayString,
				b17FruLedProperties
					DisplayString,
				b17FRUControl
					INTEGER,
				b17FRULabel
					DisplayString,
				b17ResetReason
					DisplayString
			 }

 		b17fruNumber OBJECT-TYPE
			SYNTAX INTEGER
			MAX-ACCESS not-accessible
			STATUS current
			DESCRIPTION
				" "
			::= { blade17FruEntry 1 }
		
 		b17FruHotSwapState OBJECT-TYPE
			SYNTAX DisplayString
			MAX-ACCESS read-only
			STATUS current
			DESCRIPTION
				"Retrieve the hot swap state of the FRU from the 
				internally known hot swap states of blade1."
			::= { blade17FruEntry 3 }
		
 		b17FruLedProperties OBJECT-TYPE
			SYNTAX DisplayString
			MAX-ACCESS read-only
			STATUS current
			DESCRIPTION
				"Retrieves the LED support information from a FRU. Returns a comma separated
				list of LEDS and the number of FRU supported user LEDs."
			::= { blade17FruEntry 4 }

		

		b17FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade17FruEntry 9 }
		
 		b17FRULabel OBJECT-TYPE
			SYNTAX DisplayString
			MAX-ACCESS read-only
			STATUS current
			DESCRIPTION
				"Get fru label of blade1."
			::= { blade17FruEntry 10 }
		
 		b17ResetReason OBJECT-TYPE
			SYNTAX DisplayString
			MAX-ACCESS read-only
			STATUS current
			DESCRIPTION
				"Delete fru label of smm."
			::= { blade17FruEntry 11 }
		
 		blade17FruLedTable OBJECT-TYPE
			SYNTAX SEQUENCE OF Blade17FruLedEntry
			MAX-ACCESS not-accessible
			STATUS current
			DESCRIPTION
				"A table containing the list of led information."
			::= { blade17 2003 }
		
 		blade17FruLedEntry OBJECT-TYPE
			SYNTAX Blade17FruLedEntry
			MAX-ACCESS not-accessible
			STATUS current
			DESCRIPTION
				"Information about a particular current led."
			INDEX { b1FruID, b1FruLed }
			::= { blade17FruLedTable 1 }
		
		Blade17FruLedEntry ::=
			SEQUENCE { 
				b17FruID
					INTEGER,
				b17FruLed
					DisplayString,
				b17FruLedColorProps
					DisplayString,
				b17FruLedState
					DisplayString
			 }

 		b17FruID OBJECT-TYPE
			SYNTAX INTEGER
			MAX-ACCESS not-accessible
			STATUS current
			DESCRIPTION
				" "
			::= { blade17FruLedEntry 1 }
		
 		b17FruLed OBJECT-TYPE
			SYNTAX DisplayString
			MAX-ACCESS not-accessible
			STATUS current
			DESCRIPTION
				" "
			::= { blade17FruLedEntry 2 }
		
 		b17FruLedColorProps OBJECT-TYPE
			SYNTAX DisplayString
			MAX-ACCESS read-only
			STATUS current
			DESCRIPTION
				"Finds out what colors are supported by the LED"
			::= { blade17FruLedEntry 3 }
		
 		b17FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade17FruLedEntry 4 }
		
 		blade17FruDescriptionTable OBJECT-TYPE
			SYNTAX SEQUENCE OF Blade17FruDescriptionEntry
			MAX-ACCESS not-accessible
			STATUS current
			DESCRIPTION
				"A table containing the list of Blade1 FRU information."
			::= { blade17 2004 }
		
 		blade17FruDescriptionEntry OBJECT-TYPE
			SYNTAX Blade17FruDescriptionEntry
			MAX-ACCESS not-accessible
			STATUS current
			DESCRIPTION
				"Information about a particular current FRU."
			INDEX { b1fruNum }
			::= { blade17FruDescriptionTable 1 }
		
		Blade17FruDescriptionEntry ::=
			SEQUENCE { 
				b17fruNum
					INTEGER,
				b17fruBoardDescription
					DisplayString,
				b17fruBoardManufacturer
					DisplayString,
				b17fruBoardPartNumber
					DisplayString,
				b17fruBoardSerialNumber
					DisplayString,
				b17fruBoardManufactureDate
					DisplayString,
				b17fruProductDescription
					DisplayString,
				b17fruProductManufacturer
					DisplayString,
				b17fruProductPartNumber
					DisplayString,
				b17fruProductSerialNumber
					DisplayString,
				b17fruProductRevision
					DisplayString,
				b17fruAll
					DisplayString
			 }

 		b17fruNum OBJECT-TYPE
			SYNTAX INTEGER
			MAX-ACCESS not-accessible
			STATUS current
			DESCRIPTION
				"blade1 FRU's INDEX"
			::= { blade17FruDescriptionEntry 1 }
		
 		b17fruBoardDescription OBJECT-TYPE
			SYNTAX DisplayString
			MAX-ACCESS read-only
			STATUS current
			DESCRIPTION
				"Used to read the Board Description from the blade1 fru."
			::= { blade17FruDescriptionEntry 2 }
		
 		b17fruBoardManufacturer OBJECT-TYPE
			SYNTAX DisplayString
			MAX-ACCESS read-only
			STATUS current
			DESCRIPTION
				"Used to read the Board Manufacturer from the blade1 fru."
			::= { blade17FruDescriptionEntry 3 }
		
 		b17fruBoardPartNumber OBJECT-TYPE
			SYNTAX DisplayString
			MAX-ACCESS read-only
			STATUS current
			DESCRIPTION
				"Used to read the Board Part Number from the blade1 fru."
			::= { blade17FruDescriptionEntry 4 }
		
 		b17fruBoardSerialNumber OBJECT-TYPE
			SYNTAX DisplayString
			MAX-ACCESS read-only
			STATUS current
			DESCRIPTION
				"Used to read the Board Serial Number from the blade1 fru."
			::= { blade17FruDescriptionEntry 5 }
		
 		b17fruBoardManufactureDate OBJECT-TYPE
			SYNTAX DisplayString
			MAX-ACCESS read-only
			STATUS current
			DESCRIPTION
				"Used to read the Board Manufacture Date from the blade1 fru."
			::= { blade17FruDescriptionEntry 6 }
		
 		b17fruProductDescription OBJECT-TYPE
			SYNTAX DisplayString
			MAX-ACCESS read-only
			STATUS current
			DESCRIPTION
				"Used to read the Product Description from the blade1 fru."
			::= { blade17FruDescriptionEntry 7 }
		
 		b17fruProductManufacturer OBJECT-TYPE
			SYNTAX DisplayString
			MAX-ACCESS read-only
			STATUS current
			DESCRIPTION
				"Used to read the Product Manufacturer from the blade1 fru."
			::= { blade17FruDescriptionEntry 8 }
		
 		b17fruProductPartNumber OBJECT-TYPE
			SYNTAX DisplayString
			MAX-ACCESS read-only
			STATUS current
			DESCRIPTION
				"Used to read the Product Part Number from the blade1 fru."
			::= { blade17FruDescriptionEntry 9 }
		
 		b17fruProductSerialNumber OBJECT-TYPE
			SYNTAX DisplayString
			MAX-ACCESS read-only
			STATUS current
			DESCRIPTION
				"Used to read the Product Serial Number from the blade1 fru."
			::= { blade17FruDescriptionEntry 10 }
		
 		b17fruProductRevision OBJECT-TYPE
			SYNTAX DisplayString
			MAX-ACCESS read-only
			STATUS current
			DESCRIPTION
				"Used to read the Product Revision from the blade1 fru."
			::= { blade17FruDescriptionEntry 13 }
		
 		b17fruAll OBJECT-TYPE
			SYNTAX DisplayString
			MAX-ACCESS read-only
			STATUS current
			DESCRIPTION
				"Used to read the fru info all."
			::= { blade17FruDescriptionEntry 14 }
		
		blade17CPUTable OBJECT-TYPE
			SYNTAX SEQUENCE OF Blade17CPUEntry
			MAX-ACCESS not-accessible
			STATUS current
			DESCRIPTION
				"A table containing the list of Blade1 FRU information."
			::= { blade17 2006 }
		
		blade17CPUEntry OBJECT-TYPE
			SYNTAX Blade17CPUEntry
			MAX-ACCESS not-accessible
			STATUS current
			DESCRIPTION
				"Information about a particular current FRU."
			INDEX { b17CPUIndex }
			::= { blade17CPUTable 1 }
		
		Blade17CPUEntry ::=
			SEQUENCE { 
				b17CPUIndex
					INTEGER,
				b17CPUMark
					DisplayString,
				b17CPUInfo
					DisplayString,
				b17CPUPresent
					INTEGER,
				b17CPUHealth
					INTEGER,
				b17CPULocation
					DisplayString
			 }

		b17CPUIndex OBJECT-TYPE
			SYNTAX INTEGER
			MAX-ACCESS not-accessible
			STATUS current
			DESCRIPTION
				"CPU INDEX"
			::= { blade17CPUEntry 1 }
		
		b17CPUMark OBJECT-TYPE
			SYNTAX DisplayString
			MAX-ACCESS read-only
			STATUS current
			DESCRIPTION
				"Get the CPU silk-screen."
			::= { blade17CPUEntry 2 }
		
		b17CPUInfo OBJECT-TYPE
			SYNTAX DisplayString
			MAX-ACCESS read-only
			STATUS current
			DESCRIPTION
				"Get the CPU description of vendor, type and frequency."
			::= { blade17CPUEntry 3 }
		
		b17CPUPresent OBJECT-TYPE
			SYNTAX INTEGER
			MAX-ACCESS read-only
			STATUS current
			DESCRIPTION
				"Get the CPU presence status."
			::= { blade17CPUEntry 4 }
		
		b17CPUHealth OBJECT-TYPE
			SYNTAX INTEGER
			MAX-ACCESS read-only
			STATUS current
			DESCRIPTION
				"Get the CPU health status."
			::= { blade17CPUEntry 5 }
		
		b17CPULocation OBJECT-TYPE
			SYNTAX DisplayString
			MAX-ACCESS read-only
			STATUS current
			DESCRIPTION
				"Get the CPU location."
			::= { blade17CPUEntry 6 }
		
		blade17MemoryTable OBJECT-TYPE
			SYNTAX SEQUENCE OF Blade17MemoryEntry
			MAX-ACCESS not-accessible
			STATUS current
			DESCRIPTION
				"A table containing the list of Blade1 FRU information."
			::= { blade17 2007 }
		
		blade17MemoryEntry OBJECT-TYPE
			SYNTAX Blade17MemoryEntry
			MAX-ACCESS not-accessible
			STATUS current
			DESCRIPTION
				"Information about a particular current FRU."
			INDEX { b17MEMIndex }
			::= { blade17MemoryTable 1 }
		
		Blade17MemoryEntry ::=
			SEQUENCE { 
				b17MEMIndex
					INTEGER,
				b17MEMMark
					DisplayString,
				b17MEMInfo
					DisplayString,
				b17MEMPresent
					INTEGER,
				b17MEMHealth
					INTEGER,
				b17MEMLocation
					DisplayString
			 }

		b17MEMIndex OBJECT-TYPE
			SYNTAX INTEGER
			MAX-ACCESS not-accessible
			STATUS current
			DESCRIPTION
				"MEMORY INDEX"
			::= { blade17MemoryEntry 1 }
		
		b17MEMMark OBJECT-TYPE
			SYNTAX DisplayString
			MAX-ACCESS read-only
			STATUS current
			DESCRIPTION
				"Get the memory silk-screen."
			::= { blade17MemoryEntry 2 }
		
		b17MEMInfo OBJECT-TYPE
			SYNTAX DisplayString
			MAX-ACCESS read-only
			STATUS current
			DESCRIPTION
				"Get the memory description of vendor, frequency and capacity."
			::= { blade17MemoryEntry 3 }
		
		b17MEMPresent OBJECT-TYPE
			SYNTAX INTEGER
			MAX-ACCESS read-only
			STATUS current
			DESCRIPTION
				"Get the memory presence status."
			::= { blade17MemoryEntry 4 }
		
		b17MEMHealth OBJECT-TYPE
			SYNTAX INTEGER
			MAX-ACCESS read-only
			STATUS current
			DESCRIPTION
				"Get the memory health status."
			::= { blade17MemoryEntry 5 }
		
		b17MEMLocation OBJECT-TYPE
			SYNTAX DisplayString
			MAX-ACCESS read-only
			STATUS current
			DESCRIPTION
				"Get the memory location."
			::= { blade17MemoryEntry 6 }
		
		blade17MezzTable OBJECT-TYPE
			SYNTAX SEQUENCE OF Blade17MezzEntry
			MAX-ACCESS not-accessible
			STATUS current
			DESCRIPTION
				"A table containing the list of Blade1 FRU information."
			::= { blade17 2008 }
		
		blade17MezzEntry OBJECT-TYPE
			SYNTAX Blade17MezzEntry
			MAX-ACCESS not-accessible
			STATUS current
			DESCRIPTION
				"Information about a particular current FRU."
			INDEX { b17MezzIndex }
			::= { blade17MezzTable 1 }
		
		Blade17MezzEntry ::=
			SEQUENCE { 
				b17MezzIndex
					INTEGER,
				b17MezzMark
					DisplayString,
				b17MezzInfo
					DisplayString,
				b17MezzPresent
					INTEGER,
				b17MezzHealth
					INTEGER,
				b17MezzLocation
					DisplayString,
				b17MezzMac
					DisplayString
			 }

		b17MezzIndex OBJECT-TYPE
			SYNTAX INTEGER
			MAX-ACCESS not-accessible
			STATUS current
			DESCRIPTION
				"MEZZ INDEX"
			::= { blade17MezzEntry 1 }
		
		b17MezzMark OBJECT-TYPE
			SYNTAX DisplayString
			MAX-ACCESS read-only
			STATUS current
			DESCRIPTION
				"Get the MEZZ silk-screen."
			::= { blade17MezzEntry 2 }
		
		b17MezzInfo OBJECT-TYPE
			SYNTAX DisplayString
			MAX-ACCESS read-only
			STATUS current
			DESCRIPTION
				"Get the MEZZ description of type."
			::= { blade17MezzEntry 3 }
		
		b17MezzPresent OBJECT-TYPE
			SYNTAX INTEGER
			MAX-ACCESS read-only
			STATUS current
			DESCRIPTION
				"Get the MEZZ presence status."
			::= { blade17MezzEntry 4 }
		
		b17MezzHealth OBJECT-TYPE
			SYNTAX INTEGER
			MAX-ACCESS read-only
			STATUS current
			DESCRIPTION
				"Get the MEZZ health status."
			::= { blade17MezzEntry 5 }
		
		b17MezzLocation OBJECT-TYPE
			SYNTAX DisplayString
			MAX-ACCESS read-only
			STATUS current
			DESCRIPTION
				"Get the MEZZ location."
			::= { blade17MezzEntry 6 }
		
		b17MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade17MezzEntry 7 }
		
		blade17DiskTable OBJECT-TYPE
			SYNTAX SEQUENCE OF Blade17DiskEntry
			MAX-ACCESS not-accessible
			STATUS current
			DESCRIPTION
				"A table containing the list of Blade1 FRU information."
			::= { blade17 2009 }
		
		blade17DiskEntry OBJECT-TYPE
			SYNTAX Blade17DiskEntry
			MAX-ACCESS not-accessible
			STATUS current
			DESCRIPTION
				"Information about a particular current FRU."
			INDEX { b17DiskIndex }
			::= { blade17DiskTable 1 }
		
		Blade17DiskEntry ::=
			SEQUENCE { 
				b17DiskIndex
					INTEGER,
				b17DiskMark
					DisplayString,
				b17DiskInfo
					DisplayString,
				b17DiskPresent
					INTEGER,
				b17DiskHealth
					INTEGER,
				b17DiskLocation
					DisplayString
			 }

		b17DiskIndex OBJECT-TYPE
			SYNTAX INTEGER
			MAX-ACCESS not-accessible
			STATUS current
			DESCRIPTION
				"DISK INDEX"
			::= { blade17DiskEntry 1 }
		
		b17DiskMark OBJECT-TYPE
			SYNTAX DisplayString
			MAX-ACCESS read-only
			STATUS current
			DESCRIPTION
				"Get the disk silk-screen."
			::= { blade17DiskEntry 2 }
		
		b17DiskInfo OBJECT-TYPE
			SYNTAX DisplayString
			MAX-ACCESS read-only
			STATUS current
			DESCRIPTION
				"Get the disk description of vendor, capacity and speed."
			::= { blade17DiskEntry 3 }
		
		b17DiskPresent OBJECT-TYPE
			SYNTAX INTEGER
			MAX-ACCESS read-only
			STATUS current
			DESCRIPTION
				"Get the disk presence status."
			::= { blade17DiskEntry 4 }
		
		b17DiskHealth OBJECT-TYPE
			SYNTAX INTEGER
			MAX-ACCESS read-only
			STATUS current
			DESCRIPTION
				"Get the disk health status."
			::= { blade17DiskEntry 5 }
		
		b17DiskLocation OBJECT-TYPE
			SYNTAX DisplayString
			MAX-ACCESS read-only
			STATUS current
			DESCRIPTION
				"Get the disk location."
			::= { blade17DiskEntry 6 }
		
		blade17SecretKvmVmmTable OBJECT-TYPE
			SYNTAX SEQUENCE OF Blade17SecretKvmVmmEntry
			MAX-ACCESS not-accessible
			STATUS current
			DESCRIPTION
				"A table containing the list of Blade17 KVM&VMM secret information."
			::= { blade17 2010 }

		blade17SecretKvmVmmEntry OBJECT-TYPE
			SYNTAX Blade17SecretKvmVmmEntry
			MAX-ACCESS not-accessible
			STATUS current
			DESCRIPTION
				"Information about a particular current KVM&VMM."
			INDEX { b17SecretKvmVmmIndex }
			::= { blade17SecretKvmVmmTable 1 }
		Blade17SecretKvmVmmEntry ::=
			SEQUENCE { 
				b17SecretKvmVmmIndex
					INTEGER,
				b17SecretKvmState
					INTEGER,
				b17SecretVmmState
					INTEGER,
				b17MMSecretVmmKey
					DisplayString,
				b17SecretVmmKey
					DisplayString
			 }
		b17SecretKvmVmmIndex OBJECT-TYPE
			SYNTAX INTEGER
			MAX-ACCESS not-accessible
			STATUS current
			DESCRIPTION
				"KVM&VMM INDEX."
			::= { blade17SecretKvmVmmEntry 1 }
		b17SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade17SecretKvmVmmEntry 2 }
		b17SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade17SecretKvmVmmEntry 3 }
		b17MMSecretVmmKey OBJECT-TYPE
			SYNTAX DisplayString
			MAX-ACCESS read-only
			STATUS current
			DESCRIPTION
				"Get the MM secret VMM key."
			::= { blade17SecretKvmVmmEntry 4 }
		b17SecretVmmKey OBJECT-TYPE
			SYNTAX DisplayString
			MAX-ACCESS read-write
			STATUS current
			DESCRIPTION
				"Set the secret VMM key."
			::= { blade17SecretKvmVmmEntry 5 }
		blade18 OBJECT IDENTIFIER ::= { blades 18 }

		
 		b18DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade18 4 }
		
 		b18PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade18 5 }
		
 		b18Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade18 6 }

		
 		b18Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade18 8 }
		
 		b18HealthEvents OBJECT-TYPE
			SYNTAX DisplayString
			MAX-ACCESS read-only
			STATUS current
			DESCRIPTION
				"Events that contribute to the b1Health of the b1Location.  
				This is a list of events currently happening on the 
				b1Location."
			::= { blade18 9 }
		
 		b18ClearSEL OBJECT-TYPE
			SYNTAX INTEGER { clear(1) }
			MAX-ACCESS read-write
			STATUS current
			DESCRIPTION
				"Clean the BMC's SEL on the board."
			::= { blade18 12 }
		
 		b18ExDiskBoardPresence OBJECT-TYPE
			SYNTAX INTEGER
				{
				not-present(0),
				present(1)
				}
			MAX-ACCESS read-only
			STATUS current
			DESCRIPTION
				"Used to find out if the extended disk board is present.
				0 - not present
				1 - present"
			::= { blade18 14 }
		
 		b18BladeVersion OBJECT-TYPE
			SYNTAX DisplayString
			MAX-ACCESS read-only
			STATUS current
			DESCRIPTION
				"display the Version of board1."
			::= { blade18 20 }
		
 		b18MACAddress OBJECT-TYPE
			SYNTAX DisplayString
			MAX-ACCESS read-only
			STATUS current
			DESCRIPTION
				"display the MACAddress of board1."
			::= { blade18 21 }
		
				
							
		
 		b18Safepwofftime OBJECT-TYPE
			SYNTAX INTEGER
			MAX-ACCESS read-write
			STATUS current
			DESCRIPTION
				"the safe poweroff time.
				"
			::= { blade18 26 }
		
 		b18BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]      
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade18 32 }
		
 		b18Systeminfo OBJECT-TYPE
			SYNTAX DisplayString
			MAX-ACCESS read-write
			STATUS current
			DESCRIPTION
				"display the system information of board1."
			::= { blade18 36 }

		
 		b18SystemProperties OBJECT-TYPE
			SYNTAX DisplayString
			MAX-ACCESS read-only
			STATUS current
			DESCRIPTION
				"Get the power of blade1."
			::= { blade18 39 }
		
 		b18BiosCfg OBJECT-TYPE
			SYNTAX DisplayString
			MAX-ACCESS read-write
			STATUS current
			DESCRIPTION
				"Get the power of blade1."
			::= { blade18 40 }
		
 		b18WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade18 41 }
		
 		b18RealTimePower OBJECT-TYPE
			SYNTAX INTEGER
			MAX-ACCESS read-only
			STATUS current
			DESCRIPTION
				" "
			::= { blade18 43 }
		
 		b18PowerCapping OBJECT-TYPE
			SYNTAX DisplayString
			MAX-ACCESS read-write
			STATUS current
			DESCRIPTION
				" "
			::= { blade18 44 }
		
 		b18Powerreference OBJECT-TYPE
			SYNTAX INTEGER
			MAX-ACCESS read-only
			STATUS current
			DESCRIPTION
				" "
			::= { blade18 45 }
		
 		b18ClearBiosConfig OBJECT-TYPE
			SYNTAX INTEGER
			MAX-ACCESS read-write
			STATUS current
			DESCRIPTION
				" "
			::= { blade18 46 }
		
 		b18BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade18 47 }
		
 		b18BmcUserAdd OBJECT-TYPE
			SYNTAX DisplayString
			MAX-ACCESS read-write
			STATUS current
			DESCRIPTION
				"Used to Add the BMC User
				settable format:
				username,passwd"
			::= { blade18 48 }
		
 		b18BmcUserDel OBJECT-TYPE
			SYNTAX DisplayString
			MAX-ACCESS read-write
			STATUS current
			DESCRIPTION
				"Used to Del the BMC User
				settable format:
				username"
			::= { blade18 49 }
		
 		b18BmcUserPasswd OBJECT-TYPE
			SYNTAX DisplayString
			MAX-ACCESS read-write
			STATUS current
			DESCRIPTION
				"Used to Change the BMC User Passwd
				settable format:
				username,passwd"
			::= { blade18 50 }
		
 		b18BmcUserpropertychg OBJECT-TYPE
			SYNTAX DisplayString
			MAX-ACCESS read-write
			STATUS current
			DESCRIPTION
				"Used to Change the BMC User Property
				settable format:
				username,property"
			::= { blade18 51 }
		
 		b18BmcGateway OBJECT-TYPE
			SYNTAX DisplayString
			MAX-ACCESS read-write
			STATUS current
			DESCRIPTION
				"Read or set the gateway."
			::= { blade18 52 }
		
 		b18SlotBitmap OBJECT-TYPE
			SYNTAX INTEGER
			MAX-ACCESS read-only
			STATUS current
			DESCRIPTION
				" "
			::= { blade18 55 }
		
		b18systemGuid OBJECT-TYPE
			SYNTAX DisplayString
			MAX-ACCESS read-only
			STATUS current
			DESCRIPTION
				" "
			::= { blade18 56 }
		
		b18ProductName OBJECT-TYPE
			SYNTAX DisplayString
			MAX-ACCESS read-only
			STATUS current
			DESCRIPTION
				"display the Version of board1."
			::= { blade18 57 }

		b18BundleVersion OBJECT-TYPE
			SYNTAX DisplayString
			MAX-ACCESS read-write
			STATUS current
			DESCRIPTION
				"Get or set the board18 bundle version."
			::= { blade18 58 }

 		blade18SensorTargetTable OBJECT-TYPE
			SYNTAX SEQUENCE OF Blade18SensorTargetEntry
			MAX-ACCESS not-accessible
			STATUS current
			DESCRIPTION
				"A table containing the list of sensor information."
			::= { blade18 2001 }
		
 		blade18SensorTargetEntry OBJECT-TYPE
			SYNTAX Blade18SensorTargetEntry
			MAX-ACCESS not-accessible
			STATUS current
			DESCRIPTION
				"Information about a particular current sensor."
			INDEX { b1Target }
			::= { blade18SensorTargetTable 1 }
		
		Blade18SensorTargetEntry ::=
			SEQUENCE { 
				b18Target
					DisplayString,
				b18Current
					DisplayString,
				b18ThresholdsAll
					DisplayString,
				b18UpperCritical
					DisplayString,
				b18UpperNonCritical
					DisplayString,
				b18UpperNonRecoverable
					DisplayString,
				b18LowerNonCritical
					DisplayString,
				b18LowerCritical
					DisplayString,
				b18LowerNonRecoverable
					DisplayString,
				b18SensorHealth
					INTEGER,
				b18SensorHealthEvents
					DisplayString,
				b18NegativeHysteresis
					DisplayString,
				b18PositiveHysteresis
					DisplayString,
				b18SensorType
					DisplayString,
				b18SensorFRUInfo
					DisplayString
			 }

 		b18Target OBJECT-TYPE
			SYNTAX DisplayString
			MAX-ACCESS not-accessible
			STATUS current
			DESCRIPTION
				"sensor Name"
			::= { blade18SensorTargetEntry 1 }
		
 		b18Current OBJECT-TYPE
			SYNTAX DisplayString
			MAX-ACCESS read-only
			STATUS current
			DESCRIPTION
				"Display the current value of a sensor."
			::= { blade18SensorTargetEntry 2 }
		
 		b18ThresholdsAll OBJECT-TYPE
			SYNTAX DisplayString
			MAX-ACCESS read-only
			STATUS current
			DESCRIPTION
				"All thresholds of a sensor"
			::= { blade18SensorTargetEntry 3 }
		
 		b18UpperCritical OBJECT-TYPE
			SYNTAX DisplayString
			MAX-ACCESS read-write
			STATUS current
			DESCRIPTION
				"Upper critical thresholds"
			::= { blade18SensorTargetEntry 4 }
		
 		b18UpperNonCritical OBJECT-TYPE
			SYNTAX DisplayString
			MAX-ACCESS read-write
			STATUS current
			DESCRIPTION
				"Upper non-critical thresholds"
			::= { blade18SensorTargetEntry 5 }
		
 		b18UpperNonRecoverable OBJECT-TYPE
			SYNTAX DisplayString
			MAX-ACCESS read-write
			STATUS current
			DESCRIPTION
				"Upper non-recoverable thresholds"
			::= { blade18SensorTargetEntry 6 }
		
 		b18LowerNonCritical OBJECT-TYPE
			SYNTAX DisplayString
			MAX-ACCESS read-write
			STATUS current
			DESCRIPTION
				"Lower non-critical thresholds"
			::= { blade18SensorTargetEntry 7 }
		
 		b18LowerCritical OBJECT-TYPE
			SYNTAX DisplayString
			MAX-ACCESS read-write
			STATUS current
			DESCRIPTION
				"Lower critical thresholds"
			::= { blade18SensorTargetEntry 8 }
		
 		b18LowerNonRecoverable OBJECT-TYPE
			SYNTAX DisplayString
			MAX-ACCESS read-write
			STATUS current
			DESCRIPTION
				"Lower non-recoverable thresholds"
			::= { blade18SensorTargetEntry 9 }
		
 		b18SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade18SensorTargetEntry 10 }
		
 		b18SensorHealthEvents OBJECT-TYPE
			SYNTAX DisplayString
			MAX-ACCESS read-only
			STATUS current
			DESCRIPTION
				"Events that contribute to the b1Health of the b1Location.  
				This is a list of events currently happening on the 
				b1Location."
			::= { blade18SensorTargetEntry 11 }
		
		
 		b18NegativeHysteresis OBJECT-TYPE
			SYNTAX DisplayString
			MAX-ACCESS read-write
			STATUS current
			DESCRIPTION
				"Get/Set the negativeHysteresis value."
			::= { blade18SensorTargetEntry 16 }
		
 		b18PositiveHysteresis OBJECT-TYPE
			SYNTAX DisplayString
			MAX-ACCESS read-write
			STATUS current
			DESCRIPTION
				"Get/Set the positiveHysteresis value."
			::= { blade18SensorTargetEntry 17 }
		
 		b18SensorType OBJECT-TYPE
			SYNTAX DisplayString
			MAX-ACCESS read-only
			STATUS current
			DESCRIPTION
				"Get the type of the sensor."
			::= { blade18SensorTargetEntry 18 }
		
 		b18SensorFRUInfo OBJECT-TYPE
			SYNTAX DisplayString
			MAX-ACCESS read-only
			STATUS current
			DESCRIPTION
				"Get the fruinfo of the sensor."
			::= { blade18SensorTargetEntry 19 }
		
 		blade18FruTable OBJECT-TYPE
			SYNTAX SEQUENCE OF Blade18FruEntry
			MAX-ACCESS not-accessible
			STATUS current
			DESCRIPTION
				"A table containing the list of FRU information."
			::= { blade18 2002 }
		
 		blade18FruEntry OBJECT-TYPE
			SYNTAX Blade18FruEntry
			MAX-ACCESS not-accessible
			STATUS current
			DESCRIPTION
				"Information about a particular current FRU."
			INDEX { b1fruNumber }
			::= { blade18FruTable 1 }
		
		Blade18FruEntry ::=
			SEQUENCE { 
				b18fruNumber
					INTEGER,
				b18FruHotSwapState
					DisplayString,
				b18FruLedProperties
					DisplayString,
				b18FRUControl
					INTEGER,
				b18FRULabel
					DisplayString,
				b18ResetReason
					DisplayString
			 }

 		b18fruNumber OBJECT-TYPE
			SYNTAX INTEGER
			MAX-ACCESS not-accessible
			STATUS current
			DESCRIPTION
				" "
			::= { blade18FruEntry 1 }
		
 		b18FruHotSwapState OBJECT-TYPE
			SYNTAX DisplayString
			MAX-ACCESS read-only
			STATUS current
			DESCRIPTION
				"Retrieve the hot swap state of the FRU from the 
				internally known hot swap states of blade1."
			::= { blade18FruEntry 3 }
		
 		b18FruLedProperties OBJECT-TYPE
			SYNTAX DisplayString
			MAX-ACCESS read-only
			STATUS current
			DESCRIPTION
				"Retrieves the LED support information from a FRU. Returns a comma separated
				list of LEDS and the number of FRU supported user LEDs."
			::= { blade18FruEntry 4 }

		

		b18FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade18FruEntry 9 }
		
 		b18FRULabel OBJECT-TYPE
			SYNTAX DisplayString
			MAX-ACCESS read-only
			STATUS current
			DESCRIPTION
				"Get fru label of blade1."
			::= { blade18FruEntry 10 }
		
 		b18ResetReason OBJECT-TYPE
			SYNTAX DisplayString
			MAX-ACCESS read-only
			STATUS current
			DESCRIPTION
				"Delete fru label of smm."
			::= { blade18FruEntry 11 }
		
 		blade18FruLedTable OBJECT-TYPE
			SYNTAX SEQUENCE OF Blade18FruLedEntry
			MAX-ACCESS not-accessible
			STATUS current
			DESCRIPTION
				"A table containing the list of led information."
			::= { blade18 2003 }
		
 		blade18FruLedEntry OBJECT-TYPE
			SYNTAX Blade18FruLedEntry
			MAX-ACCESS not-accessible
			STATUS current
			DESCRIPTION
				"Information about a particular current led."
			INDEX { b1FruID, b1FruLed }
			::= { blade18FruLedTable 1 }
		
		Blade18FruLedEntry ::=
			SEQUENCE { 
				b18FruID
					INTEGER,
				b18FruLed
					DisplayString,
				b18FruLedColorProps
					DisplayString,
				b18FruLedState
					DisplayString
			 }

 		b18FruID OBJECT-TYPE
			SYNTAX INTEGER
			MAX-ACCESS not-accessible
			STATUS current
			DESCRIPTION
				" "
			::= { blade18FruLedEntry 1 }
		
 		b18FruLed OBJECT-TYPE
			SYNTAX DisplayString
			MAX-ACCESS not-accessible
			STATUS current
			DESCRIPTION
				" "
			::= { blade18FruLedEntry 2 }
		
 		b18FruLedColorProps OBJECT-TYPE
			SYNTAX DisplayString
			MAX-ACCESS read-only
			STATUS current
			DESCRIPTION
				"Finds out what colors are supported by the LED"
			::= { blade18FruLedEntry 3 }
		
 		b18FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade18FruLedEntry 4 }
		
 		blade18FruDescriptionTable OBJECT-TYPE
			SYNTAX SEQUENCE OF Blade18FruDescriptionEntry
			MAX-ACCESS not-accessible
			STATUS current
			DESCRIPTION
				"A table containing the list of Blade1 FRU information."
			::= { blade18 2004 }
		
 		blade18FruDescriptionEntry OBJECT-TYPE
			SYNTAX Blade18FruDescriptionEntry
			MAX-ACCESS not-accessible
			STATUS current
			DESCRIPTION
				"Information about a particular current FRU."
			INDEX { b1fruNum }
			::= { blade18FruDescriptionTable 1 }
		
		Blade18FruDescriptionEntry ::=
			SEQUENCE { 
				b18fruNum
					INTEGER,
				b18fruBoardDescription
					DisplayString,
				b18fruBoardManufacturer
					DisplayString,
				b18fruBoardPartNumber
					DisplayString,
				b18fruBoardSerialNumber
					DisplayString,
				b18fruBoardManufactureDate
					DisplayString,
				b18fruProductDescription
					DisplayString,
				b18fruProductManufacturer
					DisplayString,
				b18fruProductPartNumber
					DisplayString,
				b18fruProductSerialNumber
					DisplayString,
				b18fruProductRevision
					DisplayString,
				b18fruAll
					DisplayString
			 }

 		b18fruNum OBJECT-TYPE
			SYNTAX INTEGER
			MAX-ACCESS not-accessible
			STATUS current
			DESCRIPTION
				"blade1 FRU's INDEX"
			::= { blade18FruDescriptionEntry 1 }
		
 		b18fruBoardDescription OBJECT-TYPE
			SYNTAX DisplayString
			MAX-ACCESS read-only
			STATUS current
			DESCRIPTION
				"Used to read the Board Description from the blade1 fru."
			::= { blade18FruDescriptionEntry 2 }
		
 		b18fruBoardManufacturer OBJECT-TYPE
			SYNTAX DisplayString
			MAX-ACCESS read-only
			STATUS current
			DESCRIPTION
				"Used to read the Board Manufacturer from the blade1 fru."
			::= { blade18FruDescriptionEntry 3 }
		
 		b18fruBoardPartNumber OBJECT-TYPE
			SYNTAX DisplayString
			MAX-ACCESS read-only
			STATUS current
			DESCRIPTION
				"Used to read the Board Part Number from the blade1 fru."
			::= { blade18FruDescriptionEntry 4 }
		
 		b18fruBoardSerialNumber OBJECT-TYPE
			SYNTAX DisplayString
			MAX-ACCESS read-only
			STATUS current
			DESCRIPTION
				"Used to read the Board Serial Number from the blade1 fru."
			::= { blade18FruDescriptionEntry 5 }
		
 		b18fruBoardManufactureDate OBJECT-TYPE
			SYNTAX DisplayString
			MAX-ACCESS read-only
			STATUS current
			DESCRIPTION
				"Used to read the Board Manufacture Date from the blade1 fru."
			::= { blade18FruDescriptionEntry 6 }
		
 		b18fruProductDescription OBJECT-TYPE
			SYNTAX DisplayString
			MAX-ACCESS read-only
			STATUS current
			DESCRIPTION
				"Used to read the Product Description from the blade1 fru."
			::= { blade18FruDescriptionEntry 7 }
		
 		b18fruProductManufacturer OBJECT-TYPE
			SYNTAX DisplayString
			MAX-ACCESS read-only
			STATUS current
			DESCRIPTION
				"Used to read the Product Manufacturer from the blade1 fru."
			::= { blade18FruDescriptionEntry 8 }
		
 		b18fruProductPartNumber OBJECT-TYPE
			SYNTAX DisplayString
			MAX-ACCESS read-only
			STATUS current
			DESCRIPTION
				"Used to read the Product Part Number from the blade1 fru."
			::= { blade18FruDescriptionEntry 9 }
		
 		b18fruProductSerialNumber OBJECT-TYPE
			SYNTAX DisplayString
			MAX-ACCESS read-only
			STATUS current
			DESCRIPTION
				"Used to read the Product Serial Number from the blade1 fru."
			::= { blade18FruDescriptionEntry 10 }
		
 		b18fruProductRevision OBJECT-TYPE
			SYNTAX DisplayString
			MAX-ACCESS read-only
			STATUS current
			DESCRIPTION
				"Used to read the Product Revision from the blade1 fru."
			::= { blade18FruDescriptionEntry 13 }
		
 		b18fruAll OBJECT-TYPE
			SYNTAX DisplayString
			MAX-ACCESS read-only
			STATUS current
			DESCRIPTION
				"Used to read the fru info all."
			::= { blade18FruDescriptionEntry 14 }
		
		blade18CPUTable OBJECT-TYPE
			SYNTAX SEQUENCE OF Blade18CPUEntry
			MAX-ACCESS not-accessible
			STATUS current
			DESCRIPTION
				"A table containing the list of Blade1 FRU information."
			::= { blade18 2006 }
		
		blade18CPUEntry OBJECT-TYPE
			SYNTAX Blade18CPUEntry
			MAX-ACCESS not-accessible
			STATUS current
			DESCRIPTION
				"Information about a particular current FRU."
			INDEX { b18CPUIndex }
			::= { blade18CPUTable 1 }
		
		Blade18CPUEntry ::=
			SEQUENCE { 
				b18CPUIndex
					INTEGER,
				b18CPUMark
					DisplayString,
				b18CPUInfo
					DisplayString,
				b18CPUPresent
					INTEGER,
				b18CPUHealth
					INTEGER,
				b18CPULocation
					DisplayString
			 }

		b18CPUIndex OBJECT-TYPE
			SYNTAX INTEGER
			MAX-ACCESS not-accessible
			STATUS current
			DESCRIPTION
				"CPU INDEX"
			::= { blade18CPUEntry 1 }
		
		b18CPUMark OBJECT-TYPE
			SYNTAX DisplayString
			MAX-ACCESS read-only
			STATUS current
			DESCRIPTION
				"Get the CPU silk-screen."
			::= { blade18CPUEntry 2 }
		
		b18CPUInfo OBJECT-TYPE
			SYNTAX DisplayString
			MAX-ACCESS read-only
			STATUS current
			DESCRIPTION
				"Get the CPU description of vendor, type and frequency."
			::= { blade18CPUEntry 3 }
		
		b18CPUPresent OBJECT-TYPE
			SYNTAX INTEGER
			MAX-ACCESS read-only
			STATUS current
			DESCRIPTION
				"Get the CPU presence status."
			::= { blade18CPUEntry 4 }
		
		b18CPUHealth OBJECT-TYPE
			SYNTAX INTEGER
			MAX-ACCESS read-only
			STATUS current
			DESCRIPTION
				"Get the CPU health status."
			::= { blade18CPUEntry 5 }
		
		b18CPULocation OBJECT-TYPE
			SYNTAX DisplayString
			MAX-ACCESS read-only
			STATUS current
			DESCRIPTION
				"Get the CPU location."
			::= { blade18CPUEntry 6 }
		
		blade18MemoryTable OBJECT-TYPE
			SYNTAX SEQUENCE OF Blade18MemoryEntry
			MAX-ACCESS not-accessible
			STATUS current
			DESCRIPTION
				"A table containing the list of Blade1 FRU information."
			::= { blade18 2007 }
		
		blade18MemoryEntry OBJECT-TYPE
			SYNTAX Blade18MemoryEntry
			MAX-ACCESS not-accessible
			STATUS current
			DESCRIPTION
				"Information about a particular current FRU."
			INDEX { b18MEMIndex }
			::= { blade18MemoryTable 1 }
		
		Blade18MemoryEntry ::=
			SEQUENCE { 
				b18MEMIndex
					INTEGER,
				b18MEMMark
					DisplayString,
				b18MEMInfo
					DisplayString,
				b18MEMPresent
					INTEGER,
				b18MEMHealth
					INTEGER,
				b18MEMLocation
					DisplayString
			 }

		b18MEMIndex OBJECT-TYPE
			SYNTAX INTEGER
			MAX-ACCESS not-accessible
			STATUS current
			DESCRIPTION
				"MEMORY INDEX"
			::= { blade18MemoryEntry 1 }
		
		b18MEMMark OBJECT-TYPE
			SYNTAX DisplayString
			MAX-ACCESS read-only
			STATUS current
			DESCRIPTION
				"Get the memory silk-screen."
			::= { blade18MemoryEntry 2 }
		
		b18MEMInfo OBJECT-TYPE
			SYNTAX DisplayString
			MAX-ACCESS read-only
			STATUS current
			DESCRIPTION
				"Get the memory description of vendor, frequency and capacity."
			::= { blade18MemoryEntry 3 }
		
		b18MEMPresent OBJECT-TYPE
			SYNTAX INTEGER
			MAX-ACCESS read-only
			STATUS current
			DESCRIPTION
				"Get the memory presence status."
			::= { blade18MemoryEntry 4 }
		
		b18MEMHealth OBJECT-TYPE
			SYNTAX INTEGER
			MAX-ACCESS read-only
			STATUS current
			DESCRIPTION
				"Get the memory health status."
			::= { blade18MemoryEntry 5 }
		
		b18MEMLocation OBJECT-TYPE
			SYNTAX DisplayString
			MAX-ACCESS read-only
			STATUS current
			DESCRIPTION
				"Get the memory location."
			::= { blade18MemoryEntry 6 }
		
		blade18MezzTable OBJECT-TYPE
			SYNTAX SEQUENCE OF Blade18MezzEntry
			MAX-ACCESS not-accessible
			STATUS current
			DESCRIPTION
				"A table containing the list of Blade1 FRU information."
			::= { blade18 2008 }
		
		blade18MezzEntry OBJECT-TYPE
			SYNTAX Blade18MezzEntry
			MAX-ACCESS not-accessible
			STATUS current
			DESCRIPTION
				"Information about a particular current FRU."
			INDEX { b18MezzIndex }
			::= { blade18MezzTable 1 }
		
		Blade18MezzEntry ::=
			SEQUENCE { 
				b18MezzIndex
					INTEGER,
				b18MezzMark
					DisplayString,
				b18MezzInfo
					DisplayString,
				b18MezzPresent
					INTEGER,
				b18MezzHealth
					INTEGER,
				b18MezzLocation
					DisplayString,
				b18MezzMac
					DisplayString
			 }

		b18MezzIndex OBJECT-TYPE
			SYNTAX INTEGER
			MAX-ACCESS not-accessible
			STATUS current
			DESCRIPTION
				"MEZZ INDEX"
			::= { blade18MezzEntry 1 }
		
		b18MezzMark OBJECT-TYPE
			SYNTAX DisplayString
			MAX-ACCESS read-only
			STATUS current
			DESCRIPTION
				"Get the MEZZ silk-screen."
			::= { blade18MezzEntry 2 }
		
		b18MezzInfo OBJECT-TYPE
			SYNTAX DisplayString
			MAX-ACCESS read-only
			STATUS current
			DESCRIPTION
				"Get the MEZZ description of type."
			::= { blade18MezzEntry 3 }
		
		b18MezzPresent OBJECT-TYPE
			SYNTAX INTEGER
			MAX-ACCESS read-only
			STATUS current
			DESCRIPTION
				"Get the MEZZ presence status."
			::= { blade18MezzEntry 4 }
		
		b18MezzHealth OBJECT-TYPE
			SYNTAX INTEGER
			MAX-ACCESS read-only
			STATUS current
			DESCRIPTION
				"Get the MEZZ health status."
			::= { blade18MezzEntry 5 }
		
		b18MezzLocation OBJECT-TYPE
			SYNTAX DisplayString
			MAX-ACCESS read-only
			STATUS current
			DESCRIPTION
				"Get the MEZZ location."
			::= { blade18MezzEntry 6 }
		
		b18MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade18MezzEntry 7 }
		
		blade18DiskTable OBJECT-TYPE
			SYNTAX SEQUENCE OF Blade18DiskEntry
			MAX-ACCESS not-accessible
			STATUS current
			DESCRIPTION
				"A table containing the list of Blade1 FRU information."
			::= { blade18 2009 }
		
		blade18DiskEntry OBJECT-TYPE
			SYNTAX Blade18DiskEntry
			MAX-ACCESS not-accessible
			STATUS current
			DESCRIPTION
				"Information about a particular current FRU."
			INDEX { b18DiskIndex }
			::= { blade18DiskTable 1 }
		
		Blade18DiskEntry ::=
			SEQUENCE { 
				b18DiskIndex
					INTEGER,
				b18DiskMark
					DisplayString,
				b18DiskInfo
					DisplayString,
				b18DiskPresent
					INTEGER,
				b18DiskHealth
					INTEGER,
				b18DiskLocation
					DisplayString
			 }

		b18DiskIndex OBJECT-TYPE
			SYNTAX INTEGER
			MAX-ACCESS not-accessible
			STATUS current
			DESCRIPTION
				"DISK INDEX"
			::= { blade18DiskEntry 1 }
		
		b18DiskMark OBJECT-TYPE
			SYNTAX DisplayString
			MAX-ACCESS read-only
			STATUS current
			DESCRIPTION
				"Get the disk silk-screen."
			::= { blade18DiskEntry 2 }
		
		b18DiskInfo OBJECT-TYPE
			SYNTAX DisplayString
			MAX-ACCESS read-only
			STATUS current
			DESCRIPTION
				"Get the disk description of vendor, capacity and speed."
			::= { blade18DiskEntry 3 }
		
		b18DiskPresent OBJECT-TYPE
			SYNTAX INTEGER
			MAX-ACCESS read-only
			STATUS current
			DESCRIPTION
				"Get the disk presence status."
			::= { blade18DiskEntry 4 }
		
		b18DiskHealth OBJECT-TYPE
			SYNTAX INTEGER
			MAX-ACCESS read-only
			STATUS current
			DESCRIPTION
				"Get the disk health status."
			::= { blade18DiskEntry 5 }
		
		b18DiskLocation OBJECT-TYPE
			SYNTAX DisplayString
			MAX-ACCESS read-only
			STATUS current
			DESCRIPTION
				"Get the disk location."
			::= { blade18DiskEntry 6 }
		
		blade18SecretKvmVmmTable OBJECT-TYPE
			SYNTAX SEQUENCE OF Blade18SecretKvmVmmEntry
			MAX-ACCESS not-accessible
			STATUS current
			DESCRIPTION
				"A table containing the list of Blade18 KVM&VMM secret information."
			::= { blade18 2010 }

		blade18SecretKvmVmmEntry OBJECT-TYPE
			SYNTAX Blade18SecretKvmVmmEntry
			MAX-ACCESS not-accessible
			STATUS current
			DESCRIPTION
				"Information about a particular current KVM&VMM."
			INDEX { b18SecretKvmVmmIndex }
			::= { blade18SecretKvmVmmTable 1 }
		Blade18SecretKvmVmmEntry ::=
			SEQUENCE { 
				b18SecretKvmVmmIndex
					INTEGER,
				b18SecretKvmState
					INTEGER,
				b18SecretVmmState
					INTEGER,
				b18MMSecretVmmKey
					DisplayString,
				b18SecretVmmKey
					DisplayString
			 }
		b18SecretKvmVmmIndex OBJECT-TYPE
			SYNTAX INTEGER
			MAX-ACCESS not-accessible
			STATUS current
			DESCRIPTION
				"KVM&VMM INDEX."
			::= { blade18SecretKvmVmmEntry 1 }
		b18SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade18SecretKvmVmmEntry 2 }
		b18SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade18SecretKvmVmmEntry 3 }
		b18MMSecretVmmKey OBJECT-TYPE
			SYNTAX DisplayString
			MAX-ACCESS read-only
			STATUS current
			DESCRIPTION
				"Get the MM secret VMM key."
			::= { blade18SecretKvmVmmEntry 4 }
		b18SecretVmmKey OBJECT-TYPE
			SYNTAX DisplayString
			MAX-ACCESS read-write
			STATUS current
			DESCRIPTION
				"Set the secret VMM key."
			::= { blade18SecretKvmVmmEntry 5 }
		blade19 OBJECT IDENTIFIER ::= { blades 19 }

		
 		b19DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade19 4 }
		
 		b19PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade19 5 }
		
 		b19Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade19 6 }

		
 		b19Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade19 8 }
		
 		b19HealthEvents OBJECT-TYPE
			SYNTAX DisplayString
			MAX-ACCESS read-only
			STATUS current
			DESCRIPTION
				"Events that contribute to the b1Health of the b1Location.  
				This is a list of events currently happening on the 
				b1Location."
			::= { blade19 9 }
		
 		b19ClearSEL OBJECT-TYPE
			SYNTAX INTEGER { clear(1) }
			MAX-ACCESS read-write
			STATUS current
			DESCRIPTION
				"Clean the BMC's SEL on the board."
			::= { blade19 12 }
		
 		b19ExDiskBoardPresence OBJECT-TYPE
			SYNTAX INTEGER
				{
				not-present(0),
				present(1)
				}
			MAX-ACCESS read-only
			STATUS current
			DESCRIPTION
				"Used to find out if the extended disk board is present.
				0 - not present
				1 - present"
			::= { blade19 14 }
		
 		b19BladeVersion OBJECT-TYPE
			SYNTAX DisplayString
			MAX-ACCESS read-only
			STATUS current
			DESCRIPTION
				"display the Version of board1."
			::= { blade19 20 }
		
 		b19MACAddress OBJECT-TYPE
			SYNTAX DisplayString
			MAX-ACCESS read-only
			STATUS current
			DESCRIPTION
				"display the MACAddress of board1."
			::= { blade19 21 }
		
				
							
		
 		b19Safepwofftime OBJECT-TYPE
			SYNTAX INTEGER
			MAX-ACCESS read-write
			STATUS current
			DESCRIPTION
				"the safe poweroff time.
				"
			::= { blade19 26 }
		
 		b19BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]    
				6=Force boot into BIOS Setup
				15=Force boot from Floppy/primary removable media           
				
				"
			::= { blade19 32 }
		
 		b19Systeminfo OBJECT-TYPE
			SYNTAX DisplayString
			MAX-ACCESS read-write
			STATUS current
			DESCRIPTION
				"display the system information of board1."
			::= { blade19 36 }

		
 		b19SystemProperties OBJECT-TYPE
			SYNTAX DisplayString
			MAX-ACCESS read-only
			STATUS current
			DESCRIPTION
				"Get the power of blade1."
			::= { blade19 39 }
		
 		b19BiosCfg OBJECT-TYPE
			SYNTAX DisplayString
			MAX-ACCESS read-write
			STATUS current
			DESCRIPTION
				"Get the power of blade1."
			::= { blade19 40 }
		
 		b19WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade19 41 }
		
 		b19RealTimePower OBJECT-TYPE
			SYNTAX INTEGER
			MAX-ACCESS read-only
			STATUS current
			DESCRIPTION
				" "
			::= { blade19 43 }
		
 		b19PowerCapping OBJECT-TYPE
			SYNTAX DisplayString
			MAX-ACCESS read-write
			STATUS current
			DESCRIPTION
				" "
			::= { blade19 44 }
		
 		b19Powerreference OBJECT-TYPE
			SYNTAX INTEGER
			MAX-ACCESS read-only
			STATUS current
			DESCRIPTION
				" "
			::= { blade19 45 }
		
 		b19ClearBiosConfig OBJECT-TYPE
			SYNTAX INTEGER
			MAX-ACCESS read-write
			STATUS current
			DESCRIPTION
				" "
			::= { blade19 46 }
		
 		b19BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade19 47 }
		
 		b19BmcUserAdd OBJECT-TYPE
			SYNTAX DisplayString
			MAX-ACCESS read-write
			STATUS current
			DESCRIPTION
				"Used to Add the BMC User
				settable format:
				username,passwd"
			::= { blade19 48 }
		
 		b19BmcUserDel OBJECT-TYPE
			SYNTAX DisplayString
			MAX-ACCESS read-write
			STATUS current
			DESCRIPTION
				"Used to Del the BMC User
				settable format:
				username"
			::= { blade19 49 }
		
 		b19BmcUserPasswd OBJECT-TYPE
			SYNTAX DisplayString
			MAX-ACCESS read-write
			STATUS current
			DESCRIPTION
				"Used to Change the BMC User Passwd
				settable format:
				username,passwd"
			::= { blade19 50 }
		
 		b19BmcUserpropertychg OBJECT-TYPE
			SYNTAX DisplayString
			MAX-ACCESS read-write
			STATUS current
			DESCRIPTION
				"Used to Change the BMC User Property
				settable format:
				username,property"
			::= { blade19 51 }
		
 		b19BmcGateway OBJECT-TYPE
			SYNTAX DisplayString
			MAX-ACCESS read-write
			STATUS current
			DESCRIPTION
				"Read or set the gateway."
			::= { blade19 52 }
		
 		b19SlotBitmap OBJECT-TYPE
			SYNTAX INTEGER
			MAX-ACCESS read-only
			STATUS current
			DESCRIPTION
				" "
			::= { blade19 55 }
		
		b19systemGuid OBJECT-TYPE
			SYNTAX DisplayString
			MAX-ACCESS read-only
			STATUS current
			DESCRIPTION
				" "
			::= { blade19 56 }
		
		b19ProductName OBJECT-TYPE
			SYNTAX DisplayString
			MAX-ACCESS read-only
			STATUS current
			DESCRIPTION
				"display the Version of board1."
			::= { blade19 57 }
		
		b19BundleVersion OBJECT-TYPE
			SYNTAX DisplayString
			MAX-ACCESS read-write
			STATUS current
			DESCRIPTION
				"Get or set the board19 bundle version."
			::= { blade19 58 }

 		blade19SensorTargetTable OBJECT-TYPE
			SYNTAX SEQUENCE OF Blade19SensorTargetEntry
			MAX-ACCESS not-accessible
			STATUS current
			DESCRIPTION
				"A table containing the list of sensor information."
			::= { blade19 2001 }
		
 		blade19SensorTargetEntry OBJECT-TYPE
			SYNTAX Blade19SensorTargetEntry
			MAX-ACCESS not-accessible
			STATUS current
			DESCRIPTION
				"Information about a particular current sensor."
			INDEX { b1Target }
			::= { blade19SensorTargetTable 1 }
		
		Blade19SensorTargetEntry ::=
			SEQUENCE { 
				b19Target
					DisplayString,
				b19Current
					DisplayString,
				b19ThresholdsAll
					DisplayString,
				b19UpperCritical
					DisplayString,
				b19UpperNonCritical
					DisplayString,
				b19UpperNonRecoverable
					DisplayString,
				b19LowerNonCritical
					DisplayString,
				b19LowerCritical
					DisplayString,
				b19LowerNonRecoverable
					DisplayString,
				b19SensorHealth
					INTEGER,
				b19SensorHealthEvents
					DisplayString,
				b19NegativeHysteresis
					DisplayString,
				b19PositiveHysteresis
					DisplayString,
				b19SensorType
					DisplayString,
				b19SensorFRUInfo
					DisplayString
			 }

 		b19Target OBJECT-TYPE
			SYNTAX DisplayString
			MAX-ACCESS not-accessible
			STATUS current
			DESCRIPTION
				"sensor Name"
			::= { blade19SensorTargetEntry 1 }
		
 		b19Current OBJECT-TYPE
			SYNTAX DisplayString
			MAX-ACCESS read-only
			STATUS current
			DESCRIPTION
				"Display the current value of a sensor."
			::= { blade19SensorTargetEntry 2 }
		
 		b19ThresholdsAll OBJECT-TYPE
			SYNTAX DisplayString
			MAX-ACCESS read-only
			STATUS current
			DESCRIPTION
				"All thresholds of a sensor"
			::= { blade19SensorTargetEntry 3 }
		
 		b19UpperCritical OBJECT-TYPE
			SYNTAX DisplayString
			MAX-ACCESS read-write
			STATUS current
			DESCRIPTION
				"Upper critical thresholds"
			::= { blade19SensorTargetEntry 4 }
		
 		b19UpperNonCritical OBJECT-TYPE
			SYNTAX DisplayString
			MAX-ACCESS read-write
			STATUS current
			DESCRIPTION
				"Upper non-critical thresholds"
			::= { blade19SensorTargetEntry 5 }
		
 		b19UpperNonRecoverable OBJECT-TYPE
			SYNTAX DisplayString
			MAX-ACCESS read-write
			STATUS current
			DESCRIPTION
				"Upper non-recoverable thresholds"
			::= { blade19SensorTargetEntry 6 }
		
 		b19LowerNonCritical OBJECT-TYPE
			SYNTAX DisplayString
			MAX-ACCESS read-write
			STATUS current
			DESCRIPTION
				"Lower non-critical thresholds"
			::= { blade19SensorTargetEntry 7 }
		
 		b19LowerCritical OBJECT-TYPE
			SYNTAX DisplayString
			MAX-ACCESS read-write
			STATUS current
			DESCRIPTION
				"Lower critical thresholds"
			::= { blade19SensorTargetEntry 8 }
		
 		b19LowerNonRecoverable OBJECT-TYPE
			SYNTAX DisplayString
			MAX-ACCESS read-write
			STATUS current
			DESCRIPTION
				"Lower non-recoverable thresholds"
			::= { blade19SensorTargetEntry 9 }
		
 		b19SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade19SensorTargetEntry 10 }
		
 		b19SensorHealthEvents OBJECT-TYPE
			SYNTAX DisplayString
			MAX-ACCESS read-only
			STATUS current
			DESCRIPTION
				"Events that contribute to the b1Health of the b1Location.  
				This is a list of events currently happening on the 
				b1Location."
			::= { blade19SensorTargetEntry 11 }
		
		
 		b19NegativeHysteresis OBJECT-TYPE
			SYNTAX DisplayString
			MAX-ACCESS read-write
			STATUS current
			DESCRIPTION
				"Get/Set the negativeHysteresis value."
			::= { blade19SensorTargetEntry 16 }
		
 		b19PositiveHysteresis OBJECT-TYPE
			SYNTAX DisplayString
			MAX-ACCESS read-write
			STATUS current
			DESCRIPTION
				"Get/Set the positiveHysteresis value."
			::= { blade19SensorTargetEntry 17 }
		
 		b19SensorType OBJECT-TYPE
			SYNTAX DisplayString
			MAX-ACCESS read-only
			STATUS current
			DESCRIPTION
				"Get the type of the sensor."
			::= { blade19SensorTargetEntry 18 }
		
 		b19SensorFRUInfo OBJECT-TYPE
			SYNTAX DisplayString
			MAX-ACCESS read-only
			STATUS current
			DESCRIPTION
				"Get the fruinfo of the sensor."
			::= { blade19SensorTargetEntry 19 }
		
 		blade19FruTable OBJECT-TYPE
			SYNTAX SEQUENCE OF Blade19FruEntry
			MAX-ACCESS not-accessible
			STATUS current
			DESCRIPTION
				"A table containing the list of FRU information."
			::= { blade19 2002 }
		
 		blade19FruEntry OBJECT-TYPE
			SYNTAX Blade19FruEntry
			MAX-ACCESS not-accessible
			STATUS current
			DESCRIPTION
				"Information about a particular current FRU."
			INDEX { b1fruNumber }
			::= { blade19FruTable 1 }
		
		Blade19FruEntry ::=
			SEQUENCE { 
				b19fruNumber
					INTEGER,
				b19FruHotSwapState
					DisplayString,
				b19FruLedProperties
					DisplayString,
				b19FRUControl
					INTEGER,
				b19FRULabel
					DisplayString,
				b19ResetReason
					DisplayString
			 }

 		b19fruNumber OBJECT-TYPE
			SYNTAX INTEGER
			MAX-ACCESS not-accessible
			STATUS current
			DESCRIPTION
				" "
			::= { blade19FruEntry 1 }
		
 		b19FruHotSwapState OBJECT-TYPE
			SYNTAX DisplayString
			MAX-ACCESS read-only
			STATUS current
			DESCRIPTION
				"Retrieve the hot swap state of the FRU from the 
				internally known hot swap states of blade1."
			::= { blade19FruEntry 3 }
		
 		b19FruLedProperties OBJECT-TYPE
			SYNTAX DisplayString
			MAX-ACCESS read-only
			STATUS current
			DESCRIPTION
				"Retrieves the LED support information from a FRU. Returns a comma separated
				list of LEDS and the number of FRU supported user LEDs."
			::= { blade19FruEntry 4 }

		

		b19FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade19FruEntry 9 }
		
 		b19FRULabel OBJECT-TYPE
			SYNTAX DisplayString
			MAX-ACCESS read-only
			STATUS current
			DESCRIPTION
				"Get fru label of blade1."
			::= { blade19FruEntry 10 }
		
 		b19ResetReason OBJECT-TYPE
			SYNTAX DisplayString
			MAX-ACCESS read-only
			STATUS current
			DESCRIPTION
				"Delete fru label of smm."
			::= { blade19FruEntry 11 }
		
 		blade19FruLedTable OBJECT-TYPE
			SYNTAX SEQUENCE OF Blade19FruLedEntry
			MAX-ACCESS not-accessible
			STATUS current
			DESCRIPTION
				"A table containing the list of led information."
			::= { blade19 2003 }
		
 		blade19FruLedEntry OBJECT-TYPE
			SYNTAX Blade19FruLedEntry
			MAX-ACCESS not-accessible
			STATUS current
			DESCRIPTION
				"Information about a particular current led."
			INDEX { b1FruID, b1FruLed }
			::= { blade19FruLedTable 1 }
		
		Blade19FruLedEntry ::=
			SEQUENCE { 
				b19FruID
					INTEGER,
				b19FruLed
					DisplayString,
				b19FruLedColorProps
					DisplayString,
				b19FruLedState
					DisplayString
			 }

 		b19FruID OBJECT-TYPE
			SYNTAX INTEGER
			MAX-ACCESS not-accessible
			STATUS current
			DESCRIPTION
				" "
			::= { blade19FruLedEntry 1 }
		
 		b19FruLed OBJECT-TYPE
			SYNTAX DisplayString
			MAX-ACCESS not-accessible
			STATUS current
			DESCRIPTION
				" "
			::= { blade19FruLedEntry 2 }
		
 		b19FruLedColorProps OBJECT-TYPE
			SYNTAX DisplayString
			MAX-ACCESS read-only
			STATUS current
			DESCRIPTION
				"Finds out what colors are supported by the LED"
			::= { blade19FruLedEntry 3 }
		
 		b19FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade19FruLedEntry 4 }
		
 		blade19FruDescriptionTable OBJECT-TYPE
			SYNTAX SEQUENCE OF Blade19FruDescriptionEntry
			MAX-ACCESS not-accessible
			STATUS current
			DESCRIPTION
				"A table containing the list of Blade1 FRU information."
			::= { blade19 2004 }
		
 		blade19FruDescriptionEntry OBJECT-TYPE
			SYNTAX Blade19FruDescriptionEntry
			MAX-ACCESS not-accessible
			STATUS current
			DESCRIPTION
				"Information about a particular current FRU."
			INDEX { b1fruNum }
			::= { blade19FruDescriptionTable 1 }
		
		Blade19FruDescriptionEntry ::=
			SEQUENCE { 
				b19fruNum
					INTEGER,
				b19fruBoardDescription
					DisplayString,
				b19fruBoardManufacturer
					DisplayString,
				b19fruBoardPartNumber
					DisplayString,
				b19fruBoardSerialNumber
					DisplayString,
				b19fruBoardManufactureDate
					DisplayString,
				b19fruProductDescription
					DisplayString,
				b19fruProductManufacturer
					DisplayString,
				b19fruProductPartNumber
					DisplayString,
				b19fruProductSerialNumber
					DisplayString,
				b19fruProductRevision
					DisplayString,
				b19fruAll
					DisplayString
			 }

 		b19fruNum OBJECT-TYPE
			SYNTAX INTEGER
			MAX-ACCESS not-accessible
			STATUS current
			DESCRIPTION
				"blade1 FRU's INDEX"
			::= { blade19FruDescriptionEntry 1 }
		
 		b19fruBoardDescription OBJECT-TYPE
			SYNTAX DisplayString
			MAX-ACCESS read-only
			STATUS current
			DESCRIPTION
				"Used to read the Board Description from the blade1 fru."
			::= { blade19FruDescriptionEntry 2 }
		
 		b19fruBoardManufacturer OBJECT-TYPE
			SYNTAX DisplayString
			MAX-ACCESS read-only
			STATUS current
			DESCRIPTION
				"Used to read the Board Manufacturer from the blade1 fru."
			::= { blade19FruDescriptionEntry 3 }
		
 		b19fruBoardPartNumber OBJECT-TYPE
			SYNTAX DisplayString
			MAX-ACCESS read-only
			STATUS current
			DESCRIPTION
				"Used to read the Board Part Number from the blade1 fru."
			::= { blade19FruDescriptionEntry 4 }
		
 		b19fruBoardSerialNumber OBJECT-TYPE
			SYNTAX DisplayString
			MAX-ACCESS read-only
			STATUS current
			DESCRIPTION
				"Used to read the Board Serial Number from the blade1 fru."
			::= { blade19FruDescriptionEntry 5 }
		
 		b19fruBoardManufactureDate OBJECT-TYPE
			SYNTAX DisplayString
			MAX-ACCESS read-only
			STATUS current
			DESCRIPTION
				"Used to read the Board Manufacture Date from the blade1 fru."
			::= { blade19FruDescriptionEntry 6 }
		
 		b19fruProductDescription OBJECT-TYPE
			SYNTAX DisplayString
			MAX-ACCESS read-only
			STATUS current
			DESCRIPTION
				"Used to read the Product Description from the blade1 fru."
			::= { blade19FruDescriptionEntry 7 }
		
 		b19fruProductManufacturer OBJECT-TYPE
			SYNTAX DisplayString
			MAX-ACCESS read-only
			STATUS current
			DESCRIPTION
				"Used to read the Product Manufacturer from the blade1 fru."
			::= { blade19FruDescriptionEntry 8 }
		
 		b19fruProductPartNumber OBJECT-TYPE
			SYNTAX DisplayString
			MAX-ACCESS read-only
			STATUS current
			DESCRIPTION
				"Used to read the Product Part Number from the blade1 fru."
			::= { blade19FruDescriptionEntry 9 }
		
 		b19fruProductSerialNumber OBJECT-TYPE
			SYNTAX DisplayString
			MAX-ACCESS read-only
			STATUS current
			DESCRIPTION
				"Used to read the Product Serial Number from the blade1 fru."
			::= { blade19FruDescriptionEntry 10 }
		
 		b19fruProductRevision OBJECT-TYPE
			SYNTAX DisplayString
			MAX-ACCESS read-only
			STATUS current
			DESCRIPTION
				"Used to read the Product Revision from the blade1 fru."
			::= { blade19FruDescriptionEntry 13 }
		
 		b19fruAll OBJECT-TYPE
			SYNTAX DisplayString
			MAX-ACCESS read-only
			STATUS current
			DESCRIPTION
				"Used to read the fru info all."
			::= { blade19FruDescriptionEntry 14 }
		
		blade19CPUTable OBJECT-TYPE
			SYNTAX SEQUENCE OF Blade19CPUEntry
			MAX-ACCESS not-accessible
			STATUS current
			DESCRIPTION
				"A table containing the list of Blade1 FRU information."
			::= { blade19 2006 }
		
		blade19CPUEntry OBJECT-TYPE
			SYNTAX Blade19CPUEntry
			MAX-ACCESS not-accessible
			STATUS current
			DESCRIPTION
				"Information about a particular current FRU."
			INDEX { b19CPUIndex }
			::= { blade19CPUTable 1 }
		
		Blade19CPUEntry ::=
			SEQUENCE { 
				b19CPUIndex
					INTEGER,
				b19CPUMark
					DisplayString,
				b19CPUInfo
					DisplayString,
				b19CPUPresent
					INTEGER,
				b19CPUHealth
					INTEGER,
				b19CPULocation
					DisplayString
			 }

		b19CPUIndex OBJECT-TYPE
			SYNTAX INTEGER
			MAX-ACCESS not-accessible
			STATUS current
			DESCRIPTION
				"CPU INDEX"
			::= { blade19CPUEntry 1 }
		
		b19CPUMark OBJECT-TYPE
			SYNTAX DisplayString
			MAX-ACCESS read-only
			STATUS current
			DESCRIPTION
				"Get the CPU silk-screen."
			::= { blade19CPUEntry 2 }
		
		b19CPUInfo OBJECT-TYPE
			SYNTAX DisplayString
			MAX-ACCESS read-only
			STATUS current
			DESCRIPTION
				"Get the CPU description of vendor, type and frequency."
			::= { blade19CPUEntry 3 }
		
		b19CPUPresent OBJECT-TYPE
			SYNTAX INTEGER
			MAX-ACCESS read-only
			STATUS current
			DESCRIPTION
				"Get the CPU presence status."
			::= { blade19CPUEntry 4 }
		
		b19CPUHealth OBJECT-TYPE
			SYNTAX INTEGER
			MAX-ACCESS read-only
			STATUS current
			DESCRIPTION
				"Get the CPU health status."
			::= { blade19CPUEntry 5 }
		
		b19CPULocation OBJECT-TYPE
			SYNTAX DisplayString
			MAX-ACCESS read-only
			STATUS current
			DESCRIPTION
				"Get the CPU location."
			::= { blade19CPUEntry 6 }
		
		blade19MemoryTable OBJECT-TYPE
			SYNTAX SEQUENCE OF Blade19MemoryEntry
			MAX-ACCESS not-accessible
			STATUS current
			DESCRIPTION
				"A table containing the list of Blade1 FRU information."
			::= { blade19 2007 }
		
		blade19MemoryEntry OBJECT-TYPE
			SYNTAX Blade19MemoryEntry
			MAX-ACCESS not-accessible
			STATUS current
			DESCRIPTION
				"Information about a particular current FRU."
			INDEX { b19MEMIndex }
			::= { blade19MemoryTable 1 }
		
		Blade19MemoryEntry ::=
			SEQUENCE { 
				b19MEMIndex
					INTEGER,
				b19MEMMark
					DisplayString,
				b19MEMInfo
					DisplayString,
				b19MEMPresent
					INTEGER,
				b19MEMHealth
					INTEGER,
				b19MEMLocation
					DisplayString
			 }

		b19MEMIndex OBJECT-TYPE
			SYNTAX INTEGER
			MAX-ACCESS not-accessible
			STATUS current
			DESCRIPTION
				"MEMORY INDEX"
			::= { blade19MemoryEntry 1 }
		
		b19MEMMark OBJECT-TYPE
			SYNTAX DisplayString
			MAX-ACCESS read-only
			STATUS current
			DESCRIPTION
				"Get the memory silk-screen."
			::= { blade19MemoryEntry 2 }
		
		b19MEMInfo OBJECT-TYPE
			SYNTAX DisplayString
			MAX-ACCESS read-only
			STATUS current
			DESCRIPTION
				"Get the memory description of vendor, frequency and capacity."
			::= { blade19MemoryEntry 3 }
		
		b19MEMPresent OBJECT-TYPE
			SYNTAX INTEGER
			MAX-ACCESS read-only
			STATUS current
			DESCRIPTION
				"Get the memory presence status."
			::= { blade19MemoryEntry 4 }
		
		b19MEMHealth OBJECT-TYPE
			SYNTAX INTEGER
			MAX-ACCESS read-only
			STATUS current
			DESCRIPTION
				"Get the memory health status."
			::= { blade19MemoryEntry 5 }
		
		b19MEMLocation OBJECT-TYPE
			SYNTAX DisplayString
			MAX-ACCESS read-only
			STATUS current
			DESCRIPTION
				"Get the memory location."
			::= { blade19MemoryEntry 6 }
		
		blade19MezzTable OBJECT-TYPE
			SYNTAX SEQUENCE OF Blade19MezzEntry
			MAX-ACCESS not-accessible
			STATUS current
			DESCRIPTION
				"A table containing the list of Blade1 FRU information."
			::= { blade19 2008 }
		
		blade19MezzEntry OBJECT-TYPE
			SYNTAX Blade19MezzEntry
			MAX-ACCESS not-accessible
			STATUS current
			DESCRIPTION
				"Information about a particular current FRU."
			INDEX { b19MezzIndex }
			::= { blade19MezzTable 1 }
		
		Blade19MezzEntry ::=
			SEQUENCE { 
				b19MezzIndex
					INTEGER,
				b19MezzMark
					DisplayString,
				b19MezzInfo
					DisplayString,
				b19MezzPresent
					INTEGER,
				b19MezzHealth
					INTEGER,
				b19MezzLocation
					DisplayString,
				b19MezzMac
					DisplayString
			 }

		b19MezzIndex OBJECT-TYPE
			SYNTAX INTEGER
			MAX-ACCESS not-accessible
			STATUS current
			DESCRIPTION
				"MEZZ INDEX"
			::= { blade19MezzEntry 1 }
		
		b19MezzMark OBJECT-TYPE
			SYNTAX DisplayString
			MAX-ACCESS read-only
			STATUS current
			DESCRIPTION
				"Get the MEZZ silk-screen."
			::= { blade19MezzEntry 2 }
		
		b19MezzInfo OBJECT-TYPE
			SYNTAX DisplayString
			MAX-ACCESS read-only
			STATUS current
			DESCRIPTION
				"Get the MEZZ description of type."
			::= { blade19MezzEntry 3 }
		
		b19MezzPresent OBJECT-TYPE
			SYNTAX INTEGER
			MAX-ACCESS read-only
			STATUS current
			DESCRIPTION
				"Get the MEZZ presence status."
			::= { blade19MezzEntry 4 }
		
		b19MezzHealth OBJECT-TYPE
			SYNTAX INTEGER
			MAX-ACCESS read-only
			STATUS current
			DESCRIPTION
				"Get the MEZZ health status."
			::= { blade19MezzEntry 5 }
		
		b19MezzLocation OBJECT-TYPE
			SYNTAX DisplayString
			MAX-ACCESS read-only
			STATUS current
			DESCRIPTION
				"Get the MEZZ location."
			::= { blade19MezzEntry 6 }
		
		b19MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade19MezzEntry 7 }
		
		blade19DiskTable OBJECT-TYPE
			SYNTAX SEQUENCE OF Blade19DiskEntry
			MAX-ACCESS not-accessible
			STATUS current
			DESCRIPTION
				"A table containing the list of Blade1 FRU information."
			::= { blade19 2009 }
		
		blade19DiskEntry OBJECT-TYPE
			SYNTAX Blade19DiskEntry
			MAX-ACCESS not-accessible
			STATUS current
			DESCRIPTION
				"Information about a particular current FRU."
			INDEX { b19DiskIndex }
			::= { blade19DiskTable 1 }
		
		Blade19DiskEntry ::=
			SEQUENCE { 
				b19DiskIndex
					INTEGER,
				b19DiskMark
					DisplayString,
				b19DiskInfo
					DisplayString,
				b19DiskPresent
					INTEGER,
				b19DiskHealth
					INTEGER,
				b19DiskLocation
					DisplayString
			 }

		b19DiskIndex OBJECT-TYPE
			SYNTAX INTEGER
			MAX-ACCESS not-accessible
			STATUS current
			DESCRIPTION
				"DISK INDEX"
			::= { blade19DiskEntry 1 }
		
		b19DiskMark OBJECT-TYPE
			SYNTAX DisplayString
			MAX-ACCESS read-only
			STATUS current
			DESCRIPTION
				"Get the disk silk-screen."
			::= { blade19DiskEntry 2 }
		
		b19DiskInfo OBJECT-TYPE
			SYNTAX DisplayString
			MAX-ACCESS read-only
			STATUS current
			DESCRIPTION
				"Get the disk description of vendor, capacity and speed."
			::= { blade19DiskEntry 3 }
		
		b19DiskPresent OBJECT-TYPE
			SYNTAX INTEGER
			MAX-ACCESS read-only
			STATUS current
			DESCRIPTION
				"Get the disk presence status."
			::= { blade19DiskEntry 4 }
		
		b19DiskHealth OBJECT-TYPE
			SYNTAX INTEGER
			MAX-ACCESS read-only
			STATUS current
			DESCRIPTION
				"Get the disk health status."
			::= { blade19DiskEntry 5 }
		
		b19DiskLocation OBJECT-TYPE
			SYNTAX DisplayString
			MAX-ACCESS read-only
			STATUS current
			DESCRIPTION
				"Get the disk location."
			::= { blade19DiskEntry 6 }
		
		blade19SecretKvmVmmTable OBJECT-TYPE
			SYNTAX SEQUENCE OF Blade19SecretKvmVmmEntry
			MAX-ACCESS not-accessible
			STATUS current
			DESCRIPTION
				"A table containing the list of Blade19 KVM&VMM secret information."
			::= { blade19 2010 }

		blade19SecretKvmVmmEntry OBJECT-TYPE
			SYNTAX Blade19SecretKvmVmmEntry
			MAX-ACCESS not-accessible
			STATUS current
			DESCRIPTION
				"Information about a particular current KVM&VMM."
			INDEX { b19SecretKvmVmmIndex }
			::= { blade19SecretKvmVmmTable 1 }
		Blade19SecretKvmVmmEntry ::=
			SEQUENCE { 
				b19SecretKvmVmmIndex
					INTEGER,
				b19SecretKvmState
					INTEGER,
				b19SecretVmmState
					INTEGER,
				b19MMSecretVmmKey
					DisplayString,
				b19SecretVmmKey
					DisplayString
			 }
		b19SecretKvmVmmIndex OBJECT-TYPE
			SYNTAX INTEGER
			MAX-ACCESS not-accessible
			STATUS current
			DESCRIPTION
				"KVM&VMM INDEX."
			::= { blade19SecretKvmVmmEntry 1 }
		b19SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade19SecretKvmVmmEntry 2 }
		b19SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade19SecretKvmVmmEntry 3 }
		b19MMSecretVmmKey OBJECT-TYPE
			SYNTAX DisplayString
			MAX-ACCESS read-only
			STATUS current
			DESCRIPTION
				"Get the MM secret VMM key."
			::= { blade19SecretKvmVmmEntry 4 }
		b19SecretVmmKey OBJECT-TYPE
			SYNTAX DisplayString
			MAX-ACCESS read-write
			STATUS current
			DESCRIPTION
				"Set the secret VMM key."
			::= { blade19SecretKvmVmmEntry 5 }
		blade20 OBJECT IDENTIFIER ::= { blades 20 }

		
 		b20DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade20 4 }
		
 		b20PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade20 5 }
		
 		b20Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade20 6 }

		
 		b20Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade20 8 }
		
 		b20HealthEvents OBJECT-TYPE
			SYNTAX DisplayString
			MAX-ACCESS read-only
			STATUS current
			DESCRIPTION
				"Events that contribute to the b1Health of the b1Location.  
				This is a list of events currently happening on the 
				b1Location."
			::= { blade20 9 }
		
 		b20ClearSEL OBJECT-TYPE
			SYNTAX INTEGER { clear(1) }
			MAX-ACCESS read-write
			STATUS current
			DESCRIPTION
				"Clean the BMC's SEL on the board."
			::= { blade20 12 }
		
 		b20ExDiskBoardPresence OBJECT-TYPE
			SYNTAX INTEGER
				{
				not-present(0),
				present(1)
				}
			MAX-ACCESS read-only
			STATUS current
			DESCRIPTION
				"Used to find out if the extended disk board is present.
				0 - not present
				1 - present"
			::= { blade20 14 }
		
 		b20BladeVersion OBJECT-TYPE
			SYNTAX DisplayString
			MAX-ACCESS read-only
			STATUS current
			DESCRIPTION
				"display the Version of board1."
			::= { blade20 20 }
		
 		b20MACAddress OBJECT-TYPE
			SYNTAX DisplayString
			MAX-ACCESS read-only
			STATUS current
			DESCRIPTION
				"display the MACAddress of board1."
			::= { blade20 21 }
		
				
							
		
 		b20Safepwofftime OBJECT-TYPE
			SYNTAX INTEGER
			MAX-ACCESS read-write
			STATUS current
			DESCRIPTION
				"the safe poweroff time.
				"
			::= { blade20 26 }
		
 		b20BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2] 
				6=Force boot into BIOS Setup
				15=Force boot from Floppy/primary removable media           
				
				"
			::= { blade20 32 }
		
 		b20Systeminfo OBJECT-TYPE
			SYNTAX DisplayString
			MAX-ACCESS read-write
			STATUS current
			DESCRIPTION
				"display the system information of board1."
			::= { blade20 36 }

		
 		b20SystemProperties OBJECT-TYPE
			SYNTAX DisplayString
			MAX-ACCESS read-only
			STATUS current
			DESCRIPTION
				"Get the power of blade1."
			::= { blade20 39 }
		
 		b20BiosCfg OBJECT-TYPE
			SYNTAX DisplayString
			MAX-ACCESS read-write
			STATUS current
			DESCRIPTION
				"Get the power of blade1."
			::= { blade20 40 }
		
 		b20WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade20 41 }
		
 		b20RealTimePower OBJECT-TYPE
			SYNTAX INTEGER
			MAX-ACCESS read-only
			STATUS current
			DESCRIPTION
				" "
			::= { blade20 43 }
		
 		b20PowerCapping OBJECT-TYPE
			SYNTAX DisplayString
			MAX-ACCESS read-write
			STATUS current
			DESCRIPTION
				" "
			::= { blade20 44 }
		
 		b20Powerreference OBJECT-TYPE
			SYNTAX INTEGER
			MAX-ACCESS read-only
			STATUS current
			DESCRIPTION
				" "
			::= { blade20 45 }
		
 		b20ClearBiosConfig OBJECT-TYPE
			SYNTAX INTEGER
			MAX-ACCESS read-write
			STATUS current
			DESCRIPTION
				" "
			::= { blade20 46 }
		
 		b20BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade20 47 }
		
 		b20BmcUserAdd OBJECT-TYPE
			SYNTAX DisplayString
			MAX-ACCESS read-write
			STATUS current
			DESCRIPTION
				"Used to Add the BMC User
				settable format:
				username,passwd"
			::= { blade20 48 }
		
 		b20BmcUserDel OBJECT-TYPE
			SYNTAX DisplayString
			MAX-ACCESS read-write
			STATUS current
			DESCRIPTION
				"Used to Del the BMC User
				settable format:
				username"
			::= { blade20 49 }
		
 		b20BmcUserPasswd OBJECT-TYPE
			SYNTAX DisplayString
			MAX-ACCESS read-write
			STATUS current
			DESCRIPTION
				"Used to Change the BMC User Passwd
				settable format:
				username,passwd"
			::= { blade20 50 }
		
 		b20BmcUserpropertychg OBJECT-TYPE
			SYNTAX DisplayString
			MAX-ACCESS read-write
			STATUS current
			DESCRIPTION
				"Used to Change the BMC User Property
				settable format:
				username,property"
			::= { blade20 51 }
		
 		b20BmcGateway OBJECT-TYPE
			SYNTAX DisplayString
			MAX-ACCESS read-write
			STATUS current
			DESCRIPTION
				"Read or set the gateway."
			::= { blade20 52 }
		
 		b20SlotBitmap OBJECT-TYPE
			SYNTAX INTEGER
			MAX-ACCESS read-only
			STATUS current
			DESCRIPTION
				" "
			::= { blade20 55 }
		
		b20systemGuid OBJECT-TYPE
			SYNTAX DisplayString
			MAX-ACCESS read-only
			STATUS current
			DESCRIPTION
				" "
			::= { blade20 56 }
		
		b20ProductName OBJECT-TYPE
			SYNTAX DisplayString
			MAX-ACCESS read-only
			STATUS current
			DESCRIPTION
				"display the Version of board1."
			::= { blade20 57 }
		
		b20BundleVersion OBJECT-TYPE
			SYNTAX DisplayString
			MAX-ACCESS read-write
			STATUS current
			DESCRIPTION
				"Get or set the board20 bundle version."
			::= { blade20 58 }

 		blade20SensorTargetTable OBJECT-TYPE
			SYNTAX SEQUENCE OF Blade20SensorTargetEntry
			MAX-ACCESS not-accessible
			STATUS current
			DESCRIPTION
				"A table containing the list of sensor information."
			::= { blade20 2001 }
		
 		blade20SensorTargetEntry OBJECT-TYPE
			SYNTAX Blade20SensorTargetEntry
			MAX-ACCESS not-accessible
			STATUS current
			DESCRIPTION
				"Information about a particular current sensor."
			INDEX { b1Target }
			::= { blade20SensorTargetTable 1 }
		
		Blade20SensorTargetEntry ::=
			SEQUENCE { 
				b20Target
					DisplayString,
				b20Current
					DisplayString,
				b20ThresholdsAll
					DisplayString,
				b20UpperCritical
					DisplayString,
				b20UpperNonCritical
					DisplayString,
				b20UpperNonRecoverable
					DisplayString,
				b20LowerNonCritical
					DisplayString,
				b20LowerCritical
					DisplayString,
				b20LowerNonRecoverable
					DisplayString,
				b20SensorHealth
					INTEGER,
				b20SensorHealthEvents
					DisplayString,
				b20NegativeHysteresis
					DisplayString,
				b20PositiveHysteresis
					DisplayString,
				b20SensorType
					DisplayString,
				b20SensorFRUInfo
					DisplayString
			 }

 		b20Target OBJECT-TYPE
			SYNTAX DisplayString
			MAX-ACCESS not-accessible
			STATUS current
			DESCRIPTION
				"sensor Name"
			::= { blade20SensorTargetEntry 1 }
		
 		b20Current OBJECT-TYPE
			SYNTAX DisplayString
			MAX-ACCESS read-only
			STATUS current
			DESCRIPTION
				"Display the current value of a sensor."
			::= { blade20SensorTargetEntry 2 }
		
 		b20ThresholdsAll OBJECT-TYPE
			SYNTAX DisplayString
			MAX-ACCESS read-only
			STATUS current
			DESCRIPTION
				"All thresholds of a sensor"
			::= { blade20SensorTargetEntry 3 }
		
 		b20UpperCritical OBJECT-TYPE
			SYNTAX DisplayString
			MAX-ACCESS read-write
			STATUS current
			DESCRIPTION
				"Upper critical thresholds"
			::= { blade20SensorTargetEntry 4 }
		
 		b20UpperNonCritical OBJECT-TYPE
			SYNTAX DisplayString
			MAX-ACCESS read-write
			STATUS current
			DESCRIPTION
				"Upper non-critical thresholds"
			::= { blade20SensorTargetEntry 5 }
		
 		b20UpperNonRecoverable OBJECT-TYPE
			SYNTAX DisplayString
			MAX-ACCESS read-write
			STATUS current
			DESCRIPTION
				"Upper non-recoverable thresholds"
			::= { blade20SensorTargetEntry 6 }
		
 		b20LowerNonCritical OBJECT-TYPE
			SYNTAX DisplayString
			MAX-ACCESS read-write
			STATUS current
			DESCRIPTION
				"Lower non-critical thresholds"
			::= { blade20SensorTargetEntry 7 }
		
 		b20LowerCritical OBJECT-TYPE
			SYNTAX DisplayString
			MAX-ACCESS read-write
			STATUS current
			DESCRIPTION
				"Lower critical thresholds"
			::= { blade20SensorTargetEntry 8 }
		
 		b20LowerNonRecoverable OBJECT-TYPE
			SYNTAX DisplayString
			MAX-ACCESS read-write
			STATUS current
			DESCRIPTION
				"Lower non-recoverable thresholds"
			::= { blade20SensorTargetEntry 9 }
		
 		b20SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade20SensorTargetEntry 10 }
		
 		b20SensorHealthEvents OBJECT-TYPE
			SYNTAX DisplayString
			MAX-ACCESS read-only
			STATUS current
			DESCRIPTION
				"Events that contribute to the b1Health of the b1Location.  
				This is a list of events currently happening on the 
				b1Location."
			::= { blade20SensorTargetEntry 11 }
		
		
 		b20NegativeHysteresis OBJECT-TYPE
			SYNTAX DisplayString
			MAX-ACCESS read-write
			STATUS current
			DESCRIPTION
				"Get/Set the negativeHysteresis value."
			::= { blade20SensorTargetEntry 16 }
		
 		b20PositiveHysteresis OBJECT-TYPE
			SYNTAX DisplayString
			MAX-ACCESS read-write
			STATUS current
			DESCRIPTION
				"Get/Set the positiveHysteresis value."
			::= { blade20SensorTargetEntry 17 }
		
 		b20SensorType OBJECT-TYPE
			SYNTAX DisplayString
			MAX-ACCESS read-only
			STATUS current
			DESCRIPTION
				"Get the type of the sensor."
			::= { blade20SensorTargetEntry 18 }
		
 		b20SensorFRUInfo OBJECT-TYPE
			SYNTAX DisplayString
			MAX-ACCESS read-only
			STATUS current
			DESCRIPTION
				"Get the fruinfo of the sensor."
			::= { blade20SensorTargetEntry 19 }
		
 		blade20FruTable OBJECT-TYPE
			SYNTAX SEQUENCE OF Blade20FruEntry
			MAX-ACCESS not-accessible
			STATUS current
			DESCRIPTION
				"A table containing the list of FRU information."
			::= { blade20 2002 }
		
 		blade20FruEntry OBJECT-TYPE
			SYNTAX Blade20FruEntry
			MAX-ACCESS not-accessible
			STATUS current
			DESCRIPTION
				"Information about a particular current FRU."
			INDEX { b1fruNumber }
			::= { blade20FruTable 1 }
		
		Blade20FruEntry ::=
			SEQUENCE { 
				b20fruNumber
					INTEGER,
				b20FruHotSwapState
					DisplayString,
				b20FruLedProperties
					DisplayString,
				b20FRUControl
					INTEGER,
				b20FRULabel
					DisplayString,
				b20ResetReason
					DisplayString
			 }

 		b20fruNumber OBJECT-TYPE
			SYNTAX INTEGER
			MAX-ACCESS not-accessible
			STATUS current
			DESCRIPTION
				" "
			::= { blade20FruEntry 1 }
		
 		b20FruHotSwapState OBJECT-TYPE
			SYNTAX DisplayString
			MAX-ACCESS read-only
			STATUS current
			DESCRIPTION
				"Retrieve the hot swap state of the FRU from the 
				internally known hot swap states of blade1."
			::= { blade20FruEntry 3 }
		
 		b20FruLedProperties OBJECT-TYPE
			SYNTAX DisplayString
			MAX-ACCESS read-only
			STATUS current
			DESCRIPTION
				"Retrieves the LED support information from a FRU. Returns a comma separated
				list of LEDS and the number of FRU supported user LEDs."
			::= { blade20FruEntry 4 }

		

		b20FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade20FruEntry 9 }
		
 		b20FRULabel OBJECT-TYPE
			SYNTAX DisplayString
			MAX-ACCESS read-only
			STATUS current
			DESCRIPTION
				"Get fru label of blade1."
			::= { blade20FruEntry 10 }
		
 		b20ResetReason OBJECT-TYPE
			SYNTAX DisplayString
			MAX-ACCESS read-only
			STATUS current
			DESCRIPTION
				"Delete fru label of smm."
			::= { blade20FruEntry 11 }
		
 		blade20FruLedTable OBJECT-TYPE
			SYNTAX SEQUENCE OF Blade20FruLedEntry
			MAX-ACCESS not-accessible
			STATUS current
			DESCRIPTION
				"A table containing the list of led information."
			::= { blade20 2003 }
		
 		blade20FruLedEntry OBJECT-TYPE
			SYNTAX Blade20FruLedEntry
			MAX-ACCESS not-accessible
			STATUS current
			DESCRIPTION
				"Information about a particular current led."
			INDEX { b1FruID, b1FruLed }
			::= { blade20FruLedTable 1 }
		
		Blade20FruLedEntry ::=
			SEQUENCE { 
				b20FruID
					INTEGER,
				b20FruLed
					DisplayString,
				b20FruLedColorProps
					DisplayString,
				b20FruLedState
					DisplayString
			 }

 		b20FruID OBJECT-TYPE
			SYNTAX INTEGER
			MAX-ACCESS not-accessible
			STATUS current
			DESCRIPTION
				" "
			::= { blade20FruLedEntry 1 }
		
 		b20FruLed OBJECT-TYPE
			SYNTAX DisplayString
			MAX-ACCESS not-accessible
			STATUS current
			DESCRIPTION
				" "
			::= { blade20FruLedEntry 2 }
		
 		b20FruLedColorProps OBJECT-TYPE
			SYNTAX DisplayString
			MAX-ACCESS read-only
			STATUS current
			DESCRIPTION
				"Finds out what colors are supported by the LED"
			::= { blade20FruLedEntry 3 }
		
 		b20FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade20FruLedEntry 4 }
		
 		blade20FruDescriptionTable OBJECT-TYPE
			SYNTAX SEQUENCE OF Blade20FruDescriptionEntry
			MAX-ACCESS not-accessible
			STATUS current
			DESCRIPTION
				"A table containing the list of Blade1 FRU information."
			::= { blade20 2004 }
		
 		blade20FruDescriptionEntry OBJECT-TYPE
			SYNTAX Blade20FruDescriptionEntry
			MAX-ACCESS not-accessible
			STATUS current
			DESCRIPTION
				"Information about a particular current FRU."
			INDEX { b1fruNum }
			::= { blade20FruDescriptionTable 1 }
		
		Blade20FruDescriptionEntry ::=
			SEQUENCE { 
				b20fruNum
					INTEGER,
				b20fruBoardDescription
					DisplayString,
				b20fruBoardManufacturer
					DisplayString,
				b20fruBoardPartNumber
					DisplayString,
				b20fruBoardSerialNumber
					DisplayString,
				b20fruBoardManufactureDate
					DisplayString,
				b20fruProductDescription
					DisplayString,
				b20fruProductManufacturer
					DisplayString,
				b20fruProductPartNumber
					DisplayString,
				b20fruProductSerialNumber
					DisplayString,
				b20fruProductRevision
					DisplayString,
				b20fruAll
					DisplayString
			 }

 		b20fruNum OBJECT-TYPE
			SYNTAX INTEGER
			MAX-ACCESS not-accessible
			STATUS current
			DESCRIPTION
				"blade1 FRU's INDEX"
			::= { blade20FruDescriptionEntry 1 }
		
 		b20fruBoardDescription OBJECT-TYPE
			SYNTAX DisplayString
			MAX-ACCESS read-only
			STATUS current
			DESCRIPTION
				"Used to read the Board Description from the blade1 fru."
			::= { blade20FruDescriptionEntry 2 }
		
 		b20fruBoardManufacturer OBJECT-TYPE
			SYNTAX DisplayString
			MAX-ACCESS read-only
			STATUS current
			DESCRIPTION
				"Used to read the Board Manufacturer from the blade1 fru."
			::= { blade20FruDescriptionEntry 3 }
		
 		b20fruBoardPartNumber OBJECT-TYPE
			SYNTAX DisplayString
			MAX-ACCESS read-only
			STATUS current
			DESCRIPTION
				"Used to read the Board Part Number from the blade1 fru."
			::= { blade20FruDescriptionEntry 4 }
		
 		b20fruBoardSerialNumber OBJECT-TYPE
			SYNTAX DisplayString
			MAX-ACCESS read-only
			STATUS current
			DESCRIPTION
				"Used to read the Board Serial Number from the blade1 fru."
			::= { blade20FruDescriptionEntry 5 }
		
 		b20fruBoardManufactureDate OBJECT-TYPE
			SYNTAX DisplayString
			MAX-ACCESS read-only
			STATUS current
			DESCRIPTION
				"Used to read the Board Manufacture Date from the blade1 fru."
			::= { blade20FruDescriptionEntry 6 }
		
 		b20fruProductDescription OBJECT-TYPE
			SYNTAX DisplayString
			MAX-ACCESS read-only
			STATUS current
			DESCRIPTION
				"Used to read the Product Description from the blade1 fru."
			::= { blade20FruDescriptionEntry 7 }
		
 		b20fruProductManufacturer OBJECT-TYPE
			SYNTAX DisplayString
			MAX-ACCESS read-only
			STATUS current
			DESCRIPTION
				"Used to read the Product Manufacturer from the blade1 fru."
			::= { blade20FruDescriptionEntry 8 }
		
 		b20fruProductPartNumber OBJECT-TYPE
			SYNTAX DisplayString
			MAX-ACCESS read-only
			STATUS current
			DESCRIPTION
				"Used to read the Product Part Number from the blade1 fru."
			::= { blade20FruDescriptionEntry 9 }
		
 		b20fruProductSerialNumber OBJECT-TYPE
			SYNTAX DisplayString
			MAX-ACCESS read-only
			STATUS current
			DESCRIPTION
				"Used to read the Product Serial Number from the blade1 fru."
			::= { blade20FruDescriptionEntry 10 }
		
 		b20fruProductRevision OBJECT-TYPE
			SYNTAX DisplayString
			MAX-ACCESS read-only
			STATUS current
			DESCRIPTION
				"Used to read the Product Revision from the blade1 fru."
			::= { blade20FruDescriptionEntry 13 }
		
 		b20fruAll OBJECT-TYPE
			SYNTAX DisplayString
			MAX-ACCESS read-only
			STATUS current
			DESCRIPTION
				"Used to read the fru info all."
			::= { blade20FruDescriptionEntry 14 }
		
		blade20CPUTable OBJECT-TYPE
			SYNTAX SEQUENCE OF Blade20CPUEntry
			MAX-ACCESS not-accessible
			STATUS current
			DESCRIPTION
				"A table containing the list of Blade1 FRU information."
			::= { blade20 2006 }
		
		blade20CPUEntry OBJECT-TYPE
			SYNTAX Blade20CPUEntry
			MAX-ACCESS not-accessible
			STATUS current
			DESCRIPTION
				"Information about a particular current FRU."
			INDEX { b20CPUIndex }
			::= { blade20CPUTable 1 }
		
		Blade20CPUEntry ::=
			SEQUENCE { 
				b20CPUIndex
					INTEGER,
				b20CPUMark
					DisplayString,
				b20CPUInfo
					DisplayString,
				b20CPUPresent
					INTEGER,
				b20CPUHealth
					INTEGER,
				b20CPULocation
					DisplayString
			 }

		b20CPUIndex OBJECT-TYPE
			SYNTAX INTEGER
			MAX-ACCESS not-accessible
			STATUS current
			DESCRIPTION
				"CPU INDEX"
			::= { blade20CPUEntry 1 }
		
		b20CPUMark OBJECT-TYPE
			SYNTAX DisplayString
			MAX-ACCESS read-only
			STATUS current
			DESCRIPTION
				"Get the CPU silk-screen."
			::= { blade20CPUEntry 2 }
		
		b20CPUInfo OBJECT-TYPE
			SYNTAX DisplayString
			MAX-ACCESS read-only
			STATUS current
			DESCRIPTION
				"Get the CPU description of vendor, type and frequency."
			::= { blade20CPUEntry 3 }
		
		b20CPUPresent OBJECT-TYPE
			SYNTAX INTEGER
			MAX-ACCESS read-only
			STATUS current
			DESCRIPTION
				"Get the CPU presence status."
			::= { blade20CPUEntry 4 }
		
		b20CPUHealth OBJECT-TYPE
			SYNTAX INTEGER
			MAX-ACCESS read-only
			STATUS current
			DESCRIPTION
				"Get the CPU health status."
			::= { blade20CPUEntry 5 }
		
		b20CPULocation OBJECT-TYPE
			SYNTAX DisplayString
			MAX-ACCESS read-only
			STATUS current
			DESCRIPTION
				"Get the CPU location."
			::= { blade20CPUEntry 6 }
		
		blade20MemoryTable OBJECT-TYPE
			SYNTAX SEQUENCE OF Blade20MemoryEntry
			MAX-ACCESS not-accessible
			STATUS current
			DESCRIPTION
				"A table containing the list of Blade1 FRU information."
			::= { blade20 2007 }
		
		blade20MemoryEntry OBJECT-TYPE
			SYNTAX Blade20MemoryEntry
			MAX-ACCESS not-accessible
			STATUS current
			DESCRIPTION
				"Information about a particular current FRU."
			INDEX { b20MEMIndex }
			::= { blade20MemoryTable 1 }
		
		Blade20MemoryEntry ::=
			SEQUENCE { 
				b20MEMIndex
					INTEGER,
				b20MEMMark
					DisplayString,
				b20MEMInfo
					DisplayString,
				b20MEMPresent
					INTEGER,
				b20MEMHealth
					INTEGER,
				b20MEMLocation
					DisplayString
			 }

		b20MEMIndex OBJECT-TYPE
			SYNTAX INTEGER
			MAX-ACCESS not-accessible
			STATUS current
			DESCRIPTION
				"MEMORY INDEX"
			::= { blade20MemoryEntry 1 }
		
		b20MEMMark OBJECT-TYPE
			SYNTAX DisplayString
			MAX-ACCESS read-only
			STATUS current
			DESCRIPTION
				"Get the memory silk-screen."
			::= { blade20MemoryEntry 2 }
		
		b20MEMInfo OBJECT-TYPE
			SYNTAX DisplayString
			MAX-ACCESS read-only
			STATUS current
			DESCRIPTION
				"Get the memory description of vendor, frequency and capacity."
			::= { blade20MemoryEntry 3 }
		
		b20MEMPresent OBJECT-TYPE
			SYNTAX INTEGER
			MAX-ACCESS read-only
			STATUS current
			DESCRIPTION
				"Get the memory presence status."
			::= { blade20MemoryEntry 4 }
		
		b20MEMHealth OBJECT-TYPE
			SYNTAX INTEGER
			MAX-ACCESS read-only
			STATUS current
			DESCRIPTION
				"Get the memory health status."
			::= { blade20MemoryEntry 5 }
		
		b20MEMLocation OBJECT-TYPE
			SYNTAX DisplayString
			MAX-ACCESS read-only
			STATUS current
			DESCRIPTION
				"Get the memory location."
			::= { blade20MemoryEntry 6 }
		
		blade20MezzTable OBJECT-TYPE
			SYNTAX SEQUENCE OF Blade20MezzEntry
			MAX-ACCESS not-accessible
			STATUS current
			DESCRIPTION
				"A table containing the list of Blade1 FRU information."
			::= { blade20 2008 }
		
		blade20MezzEntry OBJECT-TYPE
			SYNTAX Blade20MezzEntry
			MAX-ACCESS not-accessible
			STATUS current
			DESCRIPTION
				"Information about a particular current FRU."
			INDEX { b20MezzIndex }
			::= { blade20MezzTable 1 }
		
		Blade20MezzEntry ::=
			SEQUENCE { 
				b20MezzIndex
					INTEGER,
				b20MezzMark
					DisplayString,
				b20MezzInfo
					DisplayString,
				b20MezzPresent
					INTEGER,
				b20MezzHealth
					INTEGER,
				b20MezzLocation
					DisplayString,
				b20MezzMac
					DisplayString
			 }

		b20MezzIndex OBJECT-TYPE
			SYNTAX INTEGER
			MAX-ACCESS not-accessible
			STATUS current
			DESCRIPTION
				"MEZZ INDEX"
			::= { blade20MezzEntry 1 }
		
		b20MezzMark OBJECT-TYPE
			SYNTAX DisplayString
			MAX-ACCESS read-only
			STATUS current
			DESCRIPTION
				"Get the MEZZ silk-screen."
			::= { blade20MezzEntry 2 }
		
		b20MezzInfo OBJECT-TYPE
			SYNTAX DisplayString
			MAX-ACCESS read-only
			STATUS current
			DESCRIPTION
				"Get the MEZZ description of type."
			::= { blade20MezzEntry 3 }
		
		b20MezzPresent OBJECT-TYPE
			SYNTAX INTEGER
			MAX-ACCESS read-only
			STATUS current
			DESCRIPTION
				"Get the MEZZ presence status."
			::= { blade20MezzEntry 4 }
		
		b20MezzHealth OBJECT-TYPE
			SYNTAX INTEGER
			MAX-ACCESS read-only
			STATUS current
			DESCRIPTION
				"Get the MEZZ health status."
			::= { blade20MezzEntry 5 }
		
		b20MezzLocation OBJECT-TYPE
			SYNTAX DisplayString
			MAX-ACCESS read-only
			STATUS current
			DESCRIPTION
				"Get the MEZZ location."
			::= { blade20MezzEntry 6 }
		
		b20MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade20MezzEntry 7 }
		
		blade20DiskTable OBJECT-TYPE
			SYNTAX SEQUENCE OF Blade20DiskEntry
			MAX-ACCESS not-accessible
			STATUS current
			DESCRIPTION
				"A table containing the list of Blade1 FRU information."
			::= { blade20 2009 }
		
		blade20DiskEntry OBJECT-TYPE
			SYNTAX Blade20DiskEntry
			MAX-ACCESS not-accessible
			STATUS current
			DESCRIPTION
				"Information about a particular current FRU."
			INDEX { b20DiskIndex }
			::= { blade20DiskTable 1 }
		
		Blade20DiskEntry ::=
			SEQUENCE { 
				b20DiskIndex
					INTEGER,
				b20DiskMark
					DisplayString,
				b20DiskInfo
					DisplayString,
				b20DiskPresent
					INTEGER,
				b20DiskHealth
					INTEGER,
				b20DiskLocation
					DisplayString
			 }

		b20DiskIndex OBJECT-TYPE
			SYNTAX INTEGER
			MAX-ACCESS not-accessible
			STATUS current
			DESCRIPTION
				"DISK INDEX"
			::= { blade20DiskEntry 1 }
		
		b20DiskMark OBJECT-TYPE
			SYNTAX DisplayString
			MAX-ACCESS read-only
			STATUS current
			DESCRIPTION
				"Get the disk silk-screen."
			::= { blade20DiskEntry 2 }
		
		b20DiskInfo OBJECT-TYPE
			SYNTAX DisplayString
			MAX-ACCESS read-only
			STATUS current
			DESCRIPTION
				"Get the disk description of vendor, capacity and speed."
			::= { blade20DiskEntry 3 }
		
		b20DiskPresent OBJECT-TYPE
			SYNTAX INTEGER
			MAX-ACCESS read-only
			STATUS current
			DESCRIPTION
				"Get the disk presence status."
			::= { blade20DiskEntry 4 }
		
		b20DiskHealth OBJECT-TYPE
			SYNTAX INTEGER
			MAX-ACCESS read-only
			STATUS current
			DESCRIPTION
				"Get the disk health status."
			::= { blade20DiskEntry 5 }
		
		b20DiskLocation OBJECT-TYPE
			SYNTAX DisplayString
			MAX-ACCESS read-only
			STATUS current
			DESCRIPTION
				"Get the disk location."
			::= { blade20DiskEntry 6 }
		
		blade20SecretKvmVmmTable OBJECT-TYPE
			SYNTAX SEQUENCE OF Blade20SecretKvmVmmEntry
			MAX-ACCESS not-accessible
			STATUS current
			DESCRIPTION
				"A table containing the list of Blade20 KVM&VMM secret information."
			::= { blade20 2010 }

		blade20SecretKvmVmmEntry OBJECT-TYPE
			SYNTAX Blade20SecretKvmVmmEntry
			MAX-ACCESS not-accessible
			STATUS current
			DESCRIPTION
				"Information about a particular current KVM&VMM."
			INDEX { b20SecretKvmVmmIndex }
			::= { blade20SecretKvmVmmTable 1 }
		Blade20SecretKvmVmmEntry ::=
			SEQUENCE { 
				b20SecretKvmVmmIndex
					INTEGER,
				b20SecretKvmState
					INTEGER,
				b20SecretVmmState
					INTEGER,
				b20MMSecretVmmKey
					DisplayString,
				b20SecretVmmKey
					DisplayString
			 }
		b20SecretKvmVmmIndex OBJECT-TYPE
			SYNTAX INTEGER
			MAX-ACCESS not-accessible
			STATUS current
			DESCRIPTION
				"KVM&VMM INDEX."
			::= { blade20SecretKvmVmmEntry 1 }
		b20SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade20SecretKvmVmmEntry 2 }
		b20SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade20SecretKvmVmmEntry 3 }
		b20MMSecretVmmKey OBJECT-TYPE
			SYNTAX DisplayString
			MAX-ACCESS read-only
			STATUS current
			DESCRIPTION
				"Get the MM secret VMM key."
			::= { blade20SecretKvmVmmEntry 4 }
		b20SecretVmmKey OBJECT-TYPE
			SYNTAX DisplayString
			MAX-ACCESS read-write
			STATUS current
			DESCRIPTION
				"Set the secret VMM key."
			::= { blade20SecretKvmVmmEntry 5 }
		blade21 OBJECT IDENTIFIER ::= { blades 21 }

		
 		b21DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade21 4 }
		
 		b21PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade21 5 }
		
 		b21Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade21 6 }

		
 		b21Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b11Health information about a particular b11Location. 
				This will be one of the following:
				(0-ok, 1-minor, 2-major, 3-majorandminor,4-critical,5-criticalandminor,6-criticalandmajor,7-criticalandmajorandminor)"
			::= { blade21 8 }
		
 		b21HealthEvents OBJECT-TYPE
			SYNTAX DisplayString
			MAX-ACCESS read-only
			STATUS current
			DESCRIPTION
				"Events that contribute to the b11Health of the b11Location.  
				This is a list of events currently happening on the 
				b11Location."
			::= { blade21 9 }
		
 		b21ClearSEL OBJECT-TYPE
			SYNTAX INTEGER { clear(1) }
			MAX-ACCESS read-write
			STATUS current
			DESCRIPTION
				"Clean the BMC's SEL on the board."
			::= { blade21 12 }
		
 		b21ExDiskBoardPresence OBJECT-TYPE
			SYNTAX INTEGER
				{
				not-present(0),
				present(1)
				}
			MAX-ACCESS read-only
			STATUS current
			DESCRIPTION
				"Used to find out if the extended disk board is present.
				0 - not present
				1 - present"
			::= { blade21 14 }
		
 		b21BladeVersion OBJECT-TYPE
			SYNTAX DisplayString
			MAX-ACCESS read-only
			STATUS current
			DESCRIPTION
				"display the Version of board11."
			::= { blade21 20 }
		
 		b21MACAddress OBJECT-TYPE
			SYNTAX DisplayString
			MAX-ACCESS read-only
			STATUS current
			DESCRIPTION
				"display the MACAddress of board11."
			::= { blade21 21 }
		
				
							
		
 		b21Safepwofftime OBJECT-TYPE
			SYNTAX INTEGER
			MAX-ACCESS read-write
			STATUS current
			DESCRIPTION
				"the safe poweroff time.
				"
			::= { blade21 26 }
		
 		b21BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]   
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]      
				6=Force boot into BIOS Setup
				15=Force boot from Floppy/primary removable media           
				
				"
			::= { blade21 32 }
		
 		b21Systeminfo OBJECT-TYPE
			SYNTAX DisplayString
			MAX-ACCESS read-write
			STATUS current
			DESCRIPTION
				"display the system information of board11."
			::= { blade21 36 }

		
 		b21SystemProperties OBJECT-TYPE
			SYNTAX DisplayString
			MAX-ACCESS read-only
			STATUS current
			DESCRIPTION
				"Get the power of blade1."
			::= { blade21 39 }
		
 		b21BiosCfg OBJECT-TYPE
			SYNTAX DisplayString
			MAX-ACCESS read-write
			STATUS current
			DESCRIPTION
				"Get the power of blade1."
			::= { blade21 40 }
		
 		b21WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade21 41 }
		
 		b21RealTimePower OBJECT-TYPE
			SYNTAX INTEGER
			MAX-ACCESS read-only
			STATUS current
			DESCRIPTION
				" "
			::= { blade21 43 }
		
 		b21PowerCapping OBJECT-TYPE
			SYNTAX DisplayString
			MAX-ACCESS read-write
			STATUS current
			DESCRIPTION
				" "
			::= { blade21 44 }
		
 		b21Powerreference OBJECT-TYPE
			SYNTAX INTEGER
			MAX-ACCESS read-only
			STATUS current
			DESCRIPTION
				" "
			::= { blade21 45 }
		
 		b21ClearBiosConfig OBJECT-TYPE
			SYNTAX INTEGER
			MAX-ACCESS read-write
			STATUS current
			DESCRIPTION
				" "
			::= { blade21 46 }
		
 		b21BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade21 47 }
		
 		b21BmcUserAdd OBJECT-TYPE
			SYNTAX DisplayString
			MAX-ACCESS read-write
			STATUS current
			DESCRIPTION
				"Used to Add the BMC User
				settable format:
				username,passwd"
			::= { blade21 48 }
		
 		b21BmcUserDel OBJECT-TYPE
			SYNTAX DisplayString
			MAX-ACCESS read-write
			STATUS current
			DESCRIPTION
				"Used to Del the BMC User
				settable format:
				username"
			::= { blade21 49 }
		
 		b21BmcUserPasswd OBJECT-TYPE
			SYNTAX DisplayString
			MAX-ACCESS read-write
			STATUS current
			DESCRIPTION
				"Used to Change the BMC User Passwd
				settable format:
				username,passwd"
			::= { blade21 50 }
		
 		b21BmcUserpropertychg OBJECT-TYPE
			SYNTAX DisplayString
			MAX-ACCESS read-write
			STATUS current
			DESCRIPTION
				"Used to Change the BMC User Property
				settable format:
				username,property"
			::= { blade21 51 }
		
 		b21BmcGateway OBJECT-TYPE
			SYNTAX DisplayString
			MAX-ACCESS read-write
			STATUS current
			DESCRIPTION
				"Read or set the gateway."
			::= { blade21 52 }
		
 		b21SlotBitmap OBJECT-TYPE
			SYNTAX INTEGER
			MAX-ACCESS read-only
			STATUS current
			DESCRIPTION
				" "
			::= { blade21 55 }
		
		b21systemGuid OBJECT-TYPE
			SYNTAX DisplayString
			MAX-ACCESS read-only
			STATUS current
			DESCRIPTION
				" "
			::= { blade21 56 }
		
		b21ProductName OBJECT-TYPE
			SYNTAX DisplayString
			MAX-ACCESS read-only
			STATUS current
			DESCRIPTION
				"display the Version of board11."
			::= { blade21 57 }
		
		b21BundleVersion OBJECT-TYPE
			SYNTAX DisplayString
			MAX-ACCESS read-write
			STATUS current
			DESCRIPTION
				"Get or set the board21 bundle version."
			::= { blade21 58 }

 		blade21SensorTargetTable OBJECT-TYPE
			SYNTAX SEQUENCE OF Blade21SensorTargetEntry
			MAX-ACCESS not-accessible
			STATUS current
			DESCRIPTION
				"A table containing the list of sensor information."
			::= { blade21 2001 }
		
 		blade21SensorTargetEntry OBJECT-TYPE
			SYNTAX Blade21SensorTargetEntry
			MAX-ACCESS not-accessible
			STATUS current
			DESCRIPTION
				"Information about a particular current sensor."
			INDEX { b11Target }
			::= { blade21SensorTargetTable 1 }
		
		Blade21SensorTargetEntry ::=
			SEQUENCE { 
				b21Target
					DisplayString,
				b21Current
					DisplayString,
				b21ThresholdsAll
					DisplayString,
				b21UpperCritical
					DisplayString,
				b21UpperNonCritical
					DisplayString,
				b21UpperNonRecoverable
					DisplayString,
				b21LowerNonCritical
					DisplayString,
				b21LowerCritical
					DisplayString,
				b21LowerNonRecoverable
					DisplayString,
				b21SensorHealth
					INTEGER,
				b21SensorHealthEvents
					DisplayString,
				b21NegativeHysteresis
					DisplayString,
				b21PositiveHysteresis
					DisplayString,
				b21SensorType
					DisplayString,
				b21SensorFRUInfo
					DisplayString
			 }

 		b21Target OBJECT-TYPE
			SYNTAX DisplayString
			MAX-ACCESS not-accessible
			STATUS current
			DESCRIPTION
				"sensor Name"
			::= { blade21SensorTargetEntry 1 }
		
 		b21Current OBJECT-TYPE
			SYNTAX DisplayString
			MAX-ACCESS read-only
			STATUS current
			DESCRIPTION
				"Display the current value of a sensor."
			::= { blade21SensorTargetEntry 2 }
		
 		b21ThresholdsAll OBJECT-TYPE
			SYNTAX DisplayString
			MAX-ACCESS read-only
			STATUS current
			DESCRIPTION
				"All thresholds of a sensor"
			::= { blade21SensorTargetEntry 3 }
		
 		b21UpperCritical OBJECT-TYPE
			SYNTAX DisplayString
			MAX-ACCESS read-write
			STATUS current
			DESCRIPTION
				"Upper critical thresholds"
			::= { blade21SensorTargetEntry 4 }
		
 		b21UpperNonCritical OBJECT-TYPE
			SYNTAX DisplayString
			MAX-ACCESS read-write
			STATUS current
			DESCRIPTION
				"Upper non-critical thresholds"
			::= { blade21SensorTargetEntry 5 }
		
 		b21UpperNonRecoverable OBJECT-TYPE
			SYNTAX DisplayString
			MAX-ACCESS read-write
			STATUS current
			DESCRIPTION
				"Upper non-recoverable thresholds"
			::= { blade21SensorTargetEntry 6 }
		
 		b21LowerNonCritical OBJECT-TYPE
			SYNTAX DisplayString
			MAX-ACCESS read-write
			STATUS current
			DESCRIPTION
				"Lower non-critical thresholds"
			::= { blade21SensorTargetEntry 7 }
		
 		b21LowerCritical OBJECT-TYPE
			SYNTAX DisplayString
			MAX-ACCESS read-write
			STATUS current
			DESCRIPTION
				"Lower critical thresholds"
			::= { blade21SensorTargetEntry 8 }
		
 		b21LowerNonRecoverable OBJECT-TYPE
			SYNTAX DisplayString
			MAX-ACCESS read-write
			STATUS current
			DESCRIPTION
				"Lower non-recoverable thresholds"
			::= { blade21SensorTargetEntry 9 }
		
 		b21SensorHealth OBJECT-TYPE
			SYNTAX INTEGER
				{
				ok(0),
				minor(1),
				major(2),
				critical(3)
				}
			MAX-ACCESS read-only
			STATUS current
			DESCRIPTION
				"b11Health information about a particular b11Location. 
				This will be one of the following:
				(0-ok, 1-minor, 2-major, 3-critical)"
			::= { blade21SensorTargetEntry 10 }
		
 		b21SensorHealthEvents OBJECT-TYPE
			SYNTAX DisplayString
			MAX-ACCESS read-only
			STATUS current
			DESCRIPTION
				"Events that contribute to the b11Health of the b11Location.  
				This is a list of events currently happening on the 
				b11Location."
			::= { blade21SensorTargetEntry 11 }
		
		
 		b21NegativeHysteresis OBJECT-TYPE
			SYNTAX DisplayString
			MAX-ACCESS read-write
			STATUS current
			DESCRIPTION
				"Get/Set the negativeHysteresis value"
			::= { blade21SensorTargetEntry 16 }
		
 		b21PositiveHysteresis OBJECT-TYPE
			SYNTAX DisplayString
			MAX-ACCESS read-write
			STATUS current
			DESCRIPTION
				"Get/Set the positiveHysteresis value."
			::= { blade21SensorTargetEntry 17 }
		
 		b21SensorType OBJECT-TYPE
			SYNTAX DisplayString
			MAX-ACCESS read-only
			STATUS current
			DESCRIPTION
				"Get the type of the sensor."
			::= { blade21SensorTargetEntry 18 }
		
 		b21SensorFRUInfo OBJECT-TYPE
			SYNTAX DisplayString
			MAX-ACCESS read-only
			STATUS current
			DESCRIPTION
				"Get the fruinfo of the sensor."
			::= { blade21SensorTargetEntry 19 }
		
 		blade21FruTable OBJECT-TYPE
			SYNTAX SEQUENCE OF Blade21FruEntry
			MAX-ACCESS not-accessible
			STATUS current
			DESCRIPTION
				"A table containing the list of FRU information."
			::= { blade21 2002 }
		
 		blade21FruEntry OBJECT-TYPE
			SYNTAX Blade21FruEntry
			MAX-ACCESS not-accessible
			STATUS current
			DESCRIPTION
				"Information about a particular current FRU."
			INDEX { b11fruNumber }
			::= { blade21FruTable 1 }
		
		Blade21FruEntry ::=
			SEQUENCE { 
				b21fruNumber
					INTEGER,
				b21FruHotSwapState
					DisplayString,
				b21FruLedProperties
					DisplayString,
				b21FRUControl
					INTEGER,
				b21FRULabel
					DisplayString,
				b21ResetReason
					DisplayString
			 }

 		b21fruNumber OBJECT-TYPE
			SYNTAX INTEGER
			MAX-ACCESS not-accessible
			STATUS current
			DESCRIPTION
				" "
			::= { blade21FruEntry 1 }
		
 		b21FruHotSwapState OBJECT-TYPE
			SYNTAX DisplayString
			MAX-ACCESS read-only
			STATUS current
			DESCRIPTION
				"Retrieve the hot swap state of the FRU from the 
				internally known hot swap states of blade11."
			::= { blade21FruEntry 3 }
		
 		b21FruLedProperties OBJECT-TYPE
			SYNTAX DisplayString
			MAX-ACCESS read-only
			STATUS current
			DESCRIPTION
				"Retrieves the LED support information from a FRU. Returns a comma separated
				list of LEDS and the number of FRU supported user LEDs."
			::= { blade21FruEntry 4 }

		

		b21FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade21FruEntry 9 }
		
 		b21FRULabel OBJECT-TYPE
			SYNTAX DisplayString
			MAX-ACCESS read-only
			STATUS current
			DESCRIPTION
				"Get fru label of blade11."
			::= { blade21FruEntry 10 }
		
 		b21ResetReason OBJECT-TYPE
			SYNTAX DisplayString
			MAX-ACCESS read-only
			STATUS current
			DESCRIPTION
				"Delete fru label of smm."
			::= { blade21FruEntry 11 }
		
 		blade21FruLedTable OBJECT-TYPE
			SYNTAX SEQUENCE OF Blade21FruLedEntry
			MAX-ACCESS not-accessible
			STATUS current
			DESCRIPTION
				"A table containing the list of led information."
			::= { blade21 2003 }
		
 		blade21FruLedEntry OBJECT-TYPE
			SYNTAX Blade21FruLedEntry
			MAX-ACCESS not-accessible
			STATUS current
			DESCRIPTION
				"Information about a particular current led."
			INDEX { b11FruID, b11FruLed }
			::= { blade21FruLedTable 1 }
		
		Blade21FruLedEntry ::=
			SEQUENCE { 
				b21FruID
					INTEGER,
				b21FruLed
					DisplayString,
				b21FruLedColorProps
					DisplayString,
				b21FruLedState
					DisplayString
			 }

 		b21FruID OBJECT-TYPE
			SYNTAX INTEGER
			MAX-ACCESS not-accessible
			STATUS current
			DESCRIPTION
				" "
			::= { blade21FruLedEntry 1 }
		
 		b21FruLed OBJECT-TYPE
			SYNTAX DisplayString
			MAX-ACCESS not-accessible
			STATUS current
			DESCRIPTION
				" "
			::= { blade21FruLedEntry 2 }
		
 		b21FruLedColorProps OBJECT-TYPE
			SYNTAX DisplayString
			MAX-ACCESS read-only
			STATUS current
			DESCRIPTION
				"Finds out what colors are supported by the LED"
			::= { blade21FruLedEntry 3 }
		
 		b21FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade21FruLedEntry 4 }
		
 		blade21FruDescriptionTable OBJECT-TYPE
			SYNTAX SEQUENCE OF Blade21FruDescriptionEntry
			MAX-ACCESS not-accessible
			STATUS current
			DESCRIPTION
				"A table containing the list of blade11 FRU information."
			::= { blade21 2004 }
		
 		blade21FruDescriptionEntry OBJECT-TYPE
			SYNTAX Blade21FruDescriptionEntry
			MAX-ACCESS not-accessible
			STATUS current
			DESCRIPTION
				"Information about a particular current FRU."
			INDEX { b11fruNum }
			::= { blade21FruDescriptionTable 1 }
		
		Blade21FruDescriptionEntry ::=
			SEQUENCE { 
				b21fruNum
					INTEGER,
				b21fruBoardDescription
					DisplayString,
				b21fruBoardManufacturer
					DisplayString,
				b21fruBoardPartNumber
					DisplayString,
				b21fruBoardSerialNumber
					DisplayString,
				b21fruBoardManufactureDate
					DisplayString,
				b21fruProductDescription
					DisplayString,
				b21fruProductManufacturer
					DisplayString,
				b21fruProductPartNumber
					DisplayString,
				b21fruProductSerialNumber
					DisplayString,
				b21fruProductRevision
					DisplayString,
				b21fruAll
					DisplayString
			 }

 		b21fruNum OBJECT-TYPE
			SYNTAX INTEGER
			MAX-ACCESS not-accessible
			STATUS current
			DESCRIPTION
				"blade11 FRU's INDEX"
			::= { blade21FruDescriptionEntry 1 }
		
 		b21fruBoardDescription OBJECT-TYPE
			SYNTAX DisplayString
			MAX-ACCESS read-only
			STATUS current
			DESCRIPTION
				"Used to read the Board Description from the blade11 fru."
			::= { blade21FruDescriptionEntry 2 }
		
 		b21fruBoardManufacturer OBJECT-TYPE
			SYNTAX DisplayString
			MAX-ACCESS read-only
			STATUS current
			DESCRIPTION
				"Used to read the Board Manufacturer from the bladef11 fru."
			::= { blade21FruDescriptionEntry 3 }
		
 		b21fruBoardPartNumber OBJECT-TYPE
			SYNTAX DisplayString
			MAX-ACCESS read-only
			STATUS current
			DESCRIPTION
				"Used to read the Board Part Number from the blade11 fru."
			::= { blade21FruDescriptionEntry 4 }
		
 		b21fruBoardSerialNumber OBJECT-TYPE
			SYNTAX DisplayString
			MAX-ACCESS read-only
			STATUS current
			DESCRIPTION
				"Used to read the Board Serial Number from the blade11 fru."
			::= { blade21FruDescriptionEntry 5 }
		
 		b21fruBoardManufactureDate OBJECT-TYPE
			SYNTAX DisplayString
			MAX-ACCESS read-only
			STATUS current
			DESCRIPTION
				"Used to read the Board Manufacture Date from the blade11 fru."
			::= { blade21FruDescriptionEntry 6 }
		
 		b21fruProductDescription OBJECT-TYPE
			SYNTAX DisplayString
			MAX-ACCESS read-only
			STATUS current
			DESCRIPTION
				"Used to read the Product Description from the blade11 fru."
			::= { blade21FruDescriptionEntry 7 }
		
 		b21fruProductManufacturer OBJECT-TYPE
			SYNTAX DisplayString
			MAX-ACCESS read-only
			STATUS current
			DESCRIPTION
				"Used to read the Product Manufacturer from the blade11 fru."
			::= { blade21FruDescriptionEntry 8 }
		
 		b21fruProductPartNumber OBJECT-TYPE
			SYNTAX DisplayString
			MAX-ACCESS read-only
			STATUS current
			DESCRIPTION
				"Used to read the Product Part Number from the blade11 fru."
			::= { blade21FruDescriptionEntry 9 }
		
 		b21fruProductSerialNumber OBJECT-TYPE
			SYNTAX DisplayString
			MAX-ACCESS read-only
			STATUS current
			DESCRIPTION
				"Used to read the Product Serial Number from the blade11 fru."
			::= { blade21FruDescriptionEntry 10 }
		
 		b21fruProductRevision OBJECT-TYPE
			SYNTAX DisplayString
			MAX-ACCESS read-only
			STATUS current
			DESCRIPTION
				"Used to read the Product Revision from the blade11 fru."
			::= { blade21FruDescriptionEntry 13 }
		
 		b21fruAll OBJECT-TYPE
			SYNTAX DisplayString
			MAX-ACCESS read-only
			STATUS current
			DESCRIPTION
				"Used to read the fru info all."
			::= { blade21FruDescriptionEntry 14 }
		
		blade21CPUTable OBJECT-TYPE
			SYNTAX SEQUENCE OF Blade21CPUEntry
			MAX-ACCESS not-accessible
			STATUS current
			DESCRIPTION
				"A table containing the list of Blade1 FRU information."
			::= { blade21 2006 }
		
		blade21CPUEntry OBJECT-TYPE
			SYNTAX Blade21CPUEntry
			MAX-ACCESS not-accessible
			STATUS current
			DESCRIPTION
				"Information about a particular current FRU."
			INDEX { b21CPUIndex }
			::= { blade21CPUTable 1 }
		
		Blade21CPUEntry ::=
			SEQUENCE { 
				b21CPUIndex
					INTEGER,
				b21CPUMark
					DisplayString,
				b21CPUInfo
					DisplayString,
				b21CPUPresent
					INTEGER,
				b21CPUHealth
					INTEGER,
				b21CPULocation
					DisplayString
			 }

		b21CPUIndex OBJECT-TYPE
			SYNTAX INTEGER
			MAX-ACCESS not-accessible
			STATUS current
			DESCRIPTION
				"CPU INDEX"
			::= { blade21CPUEntry 1 }
		
		b21CPUMark OBJECT-TYPE
			SYNTAX DisplayString
			MAX-ACCESS read-only
			STATUS current
			DESCRIPTION
				"Get the CPU silk-screen."
			::= { blade21CPUEntry 2 }
		
		b21CPUInfo OBJECT-TYPE
			SYNTAX DisplayString
			MAX-ACCESS read-only
			STATUS current
			DESCRIPTION
				"Get the CPU description of vendor, type and frequency."
			::= { blade21CPUEntry 3 }
		
		b21CPUPresent OBJECT-TYPE
			SYNTAX INTEGER
			MAX-ACCESS read-only
			STATUS current
			DESCRIPTION
				"Get the CPU presence status."
			::= { blade21CPUEntry 4 }
		
		b21CPUHealth OBJECT-TYPE
			SYNTAX INTEGER
			MAX-ACCESS read-only
			STATUS current
			DESCRIPTION
				"Get the CPU health status."
			::= { blade21CPUEntry 5 }
		
		b21CPULocation OBJECT-TYPE
			SYNTAX DisplayString
			MAX-ACCESS read-only
			STATUS current
			DESCRIPTION
				"Get the CPU location."
			::= { blade21CPUEntry 6 }
		
		blade21MemoryTable OBJECT-TYPE
			SYNTAX SEQUENCE OF Blade21MemoryEntry
			MAX-ACCESS not-accessible
			STATUS current
			DESCRIPTION
				"A table containing the list of Blade1 FRU information."
			::= { blade21 2007 }
		
		blade21MemoryEntry OBJECT-TYPE
			SYNTAX Blade21MemoryEntry
			MAX-ACCESS not-accessible
			STATUS current
			DESCRIPTION
				"Information about a particular current FRU."
			INDEX { b21MEMIndex }
			::= { blade21MemoryTable 1 }
		
		Blade21MemoryEntry ::=
			SEQUENCE { 
				b21MEMIndex
					INTEGER,
				b21MEMMark
					DisplayString,
				b21MEMInfo
					DisplayString,
				b21MEMPresent
					INTEGER,
				b21MEMHealth
					INTEGER,
				b21MEMLocation
					DisplayString
			 }

		b21MEMIndex OBJECT-TYPE
			SYNTAX INTEGER
			MAX-ACCESS not-accessible
			STATUS current
			DESCRIPTION
				"MEMORY INDEX"
			::= { blade21MemoryEntry 1 }
		
		b21MEMMark OBJECT-TYPE
			SYNTAX DisplayString
			MAX-ACCESS read-only
			STATUS current
			DESCRIPTION
				"Get the memory silk-screen."
			::= { blade21MemoryEntry 2 }
		
		b21MEMInfo OBJECT-TYPE
			SYNTAX DisplayString
			MAX-ACCESS read-only
			STATUS current
			DESCRIPTION
				"Get the memory description of vendor, frequency and capacity."
			::= { blade21MemoryEntry 3 }
		
		b21MEMPresent OBJECT-TYPE
			SYNTAX INTEGER
			MAX-ACCESS read-only
			STATUS current
			DESCRIPTION
				"Get the memory presence status."
			::= { blade21MemoryEntry 4 }
		
		b21MEMHealth OBJECT-TYPE
			SYNTAX INTEGER
			MAX-ACCESS read-only
			STATUS current
			DESCRIPTION
				"Get the memory health status."
			::= { blade21MemoryEntry 5 }
		
		b21MEMLocation OBJECT-TYPE
			SYNTAX DisplayString
			MAX-ACCESS read-only
			STATUS current
			DESCRIPTION
				"Get the memory location."
			::= { blade21MemoryEntry 6 }
		
		blade21MezzTable OBJECT-TYPE
			SYNTAX SEQUENCE OF Blade21MezzEntry
			MAX-ACCESS not-accessible
			STATUS current
			DESCRIPTION
				"A table containing the list of Blade1 FRU information."
			::= { blade21 2008 }
		
		blade21MezzEntry OBJECT-TYPE
			SYNTAX Blade21MezzEntry
			MAX-ACCESS not-accessible
			STATUS current
			DESCRIPTION
				"Information about a particular current FRU."
			INDEX { b21MezzIndex }
			::= { blade21MezzTable 1 }
		
		Blade21MezzEntry ::=
			SEQUENCE { 
				b21MezzIndex
					INTEGER,
				b21MezzMark
					DisplayString,
				b21MezzInfo
					DisplayString,
				b21MezzPresent
					INTEGER,
				b21MezzHealth
					INTEGER,
				b21MezzLocation
					DisplayString,
				b21MezzMac
					DisplayString
			 }

		b21MezzIndex OBJECT-TYPE
			SYNTAX INTEGER
			MAX-ACCESS not-accessible
			STATUS current
			DESCRIPTION
				"MEZZ INDEX"
			::= { blade21MezzEntry 1 }
		
		b21MezzMark OBJECT-TYPE
			SYNTAX DisplayString
			MAX-ACCESS read-only
			STATUS current
			DESCRIPTION
				"Get the MEZZ silk-screen."
			::= { blade21MezzEntry 2 }
		
		b21MezzInfo OBJECT-TYPE
			SYNTAX DisplayString
			MAX-ACCESS read-only
			STATUS current
			DESCRIPTION
				"Get the MEZZ description of type."
			::= { blade21MezzEntry 3 }
		
		b21MezzPresent OBJECT-TYPE
			SYNTAX INTEGER
			MAX-ACCESS read-only
			STATUS current
			DESCRIPTION
				"Get the MEZZ presence status."
			::= { blade21MezzEntry 4 }
		
		b21MezzHealth OBJECT-TYPE
			SYNTAX INTEGER
			MAX-ACCESS read-only
			STATUS current
			DESCRIPTION
				"Get the MEZZ health status."
			::= { blade21MezzEntry 5 }
		
		b21MezzLocation OBJECT-TYPE
			SYNTAX DisplayString
			MAX-ACCESS read-only
			STATUS current
			DESCRIPTION
				"Get the MEZZ location."
			::= { blade21MezzEntry 6 }
		
		b21MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade21MezzEntry 7 }
		
		blade21DiskTable OBJECT-TYPE
			SYNTAX SEQUENCE OF Blade21DiskEntry
			MAX-ACCESS not-accessible
			STATUS current
			DESCRIPTION
				"A table containing the list of Blade1 FRU information."
			::= { blade21 2009 }
		
		blade21DiskEntry OBJECT-TYPE
			SYNTAX Blade21DiskEntry
			MAX-ACCESS not-accessible
			STATUS current
			DESCRIPTION
				"Information about a particular current FRU."
			INDEX { b21DiskIndex }
			::= { blade21DiskTable 1 }
		
		Blade21DiskEntry ::=
			SEQUENCE { 
				b21DiskIndex
					INTEGER,
				b21DiskMark
					DisplayString,
				b21DiskInfo
					DisplayString,
				b21DiskPresent
					INTEGER,
				b21DiskHealth
					INTEGER,
				b21DiskLocation
					DisplayString
			 }

		b21DiskIndex OBJECT-TYPE
			SYNTAX INTEGER
			MAX-ACCESS not-accessible
			STATUS current
			DESCRIPTION
				"DISK INDEX"
			::= { blade21DiskEntry 1 }
		
		b21DiskMark OBJECT-TYPE
			SYNTAX DisplayString
			MAX-ACCESS read-only
			STATUS current
			DESCRIPTION
				"Get the disk silk-screen."
			::= { blade21DiskEntry 2 }
		
		b21DiskInfo OBJECT-TYPE
			SYNTAX DisplayString
			MAX-ACCESS read-only
			STATUS current
			DESCRIPTION
				"Get the disk description of vendor, capacity and speed."
			::= { blade21DiskEntry 3 }
		
		b21DiskPresent OBJECT-TYPE
			SYNTAX INTEGER
			MAX-ACCESS read-only
			STATUS current
			DESCRIPTION
				"Get the disk presence status."
			::= { blade21DiskEntry 4 }
		
		b21DiskHealth OBJECT-TYPE
			SYNTAX INTEGER
			MAX-ACCESS read-only
			STATUS current
			DESCRIPTION
				"Get the disk health status."
			::= { blade21DiskEntry 5 }
		
		b21DiskLocation OBJECT-TYPE
			SYNTAX DisplayString
			MAX-ACCESS read-only
			STATUS current
			DESCRIPTION
				"Get the disk location."
			::= { blade21DiskEntry 6 }
		
		blade21SecretKvmVmmTable OBJECT-TYPE
			SYNTAX SEQUENCE OF Blade21SecretKvmVmmEntry
			MAX-ACCESS not-accessible
			STATUS current
			DESCRIPTION
				"A table containing the list of Blade21 KVM&VMM secret information."
			::= { blade21 2010 }

		blade21SecretKvmVmmEntry OBJECT-TYPE
			SYNTAX Blade21SecretKvmVmmEntry
			MAX-ACCESS not-accessible
			STATUS current
			DESCRIPTION
				"Information about a particular current KVM&VMM."
			INDEX { b21SecretKvmVmmIndex }
			::= { blade21SecretKvmVmmTable 1 }
		Blade21SecretKvmVmmEntry ::=
			SEQUENCE { 
				b21SecretKvmVmmIndex
					INTEGER,
				b21SecretKvmState
					INTEGER,
				b21SecretVmmState
					INTEGER,
				b21MMSecretVmmKey
					DisplayString,
				b21SecretVmmKey
					DisplayString
			 }
		b21SecretKvmVmmIndex OBJECT-TYPE
			SYNTAX INTEGER
			MAX-ACCESS not-accessible
			STATUS current
			DESCRIPTION
				"KVM&VMM INDEX."
			::= { blade21SecretKvmVmmEntry 1 }
		b21SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade21SecretKvmVmmEntry 2 }
		b21SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade21SecretKvmVmmEntry 3 }
		b21MMSecretVmmKey OBJECT-TYPE
			SYNTAX DisplayString
			MAX-ACCESS read-only
			STATUS current
			DESCRIPTION
				"Get the MM secret VMM key."
			::= { blade21SecretKvmVmmEntry 4 }
		b21SecretVmmKey OBJECT-TYPE
			SYNTAX DisplayString
			MAX-ACCESS read-write
			STATUS current
			DESCRIPTION
				"Set the secret VMM key."
			::= { blade21SecretKvmVmmEntry 5 }
		blade22 OBJECT IDENTIFIER ::= { blades 22 }

		
 		b22DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade22 4 }
		
 		b22PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade22 5 }
		
 		b22Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade22 6 }

		
 		b22Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b12Health information about a particular b12Location. 
				This will be one of the following:
				(0-ok, 1-minor, 2-major, 3-majorandminor,4-critical,5-criticalandminor,6-criticalandmajor,7-criticalandmajorandminor)"
			::= { blade22 8 }
		
 		b22HealthEvents OBJECT-TYPE
			SYNTAX DisplayString
			MAX-ACCESS read-only
			STATUS current
			DESCRIPTION
				"Events that contribute to the b12Health of the b12Location.  
				This is a list of events currently happening on the 
				b12Location."
			::= { blade22 9 }
		
 		b22ClearSEL OBJECT-TYPE
			SYNTAX INTEGER { clear(1) }
			MAX-ACCESS read-write
			STATUS current
			DESCRIPTION
				"Clean the BMC's SEL on the board."
			::= { blade22 12 }
		
 		b22ExDiskBoardPresence OBJECT-TYPE
			SYNTAX INTEGER
				{
				not-present(0),
				present(1)
				}
			MAX-ACCESS read-only
			STATUS current
			DESCRIPTION
				"Used to find out if the extended disk board is present.
				0 - not present
				1 - present"
			::= { blade22 14 }
		
 		b22BladeVersion OBJECT-TYPE
			SYNTAX DisplayString
			MAX-ACCESS read-only
			STATUS current
			DESCRIPTION
				"display the Version of board12."
			::= { blade22 20 }
		
 		b22MACAddress OBJECT-TYPE
			SYNTAX DisplayString
			MAX-ACCESS read-only
			STATUS current
			DESCRIPTION
				"display the MACAddress of board12."
			::= { blade22 21 }
		
				
							
		
 		b22Safepwofftime OBJECT-TYPE
			SYNTAX INTEGER
			MAX-ACCESS read-write
			STATUS current
			DESCRIPTION
				"the safe poweroff time.
				"
			::= { blade22 26 }
		
 		b22BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]  
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2] 
				6=Force boot into BIOS Setup
				15=Force boot from Floppy/primary removable media           
				
				"
			::= { blade22 32 }
		
 		b22Systeminfo OBJECT-TYPE
			SYNTAX DisplayString
			MAX-ACCESS read-write
			STATUS current
			DESCRIPTION
				"display the system information of board12."
			::= { blade22 36 }

		
 		b22SystemProperties OBJECT-TYPE
			SYNTAX DisplayString
			MAX-ACCESS read-only
			STATUS current
			DESCRIPTION
				"Get the power of blade1."
			::= { blade22 39 }
		
 		b22BiosCfg OBJECT-TYPE
			SYNTAX DisplayString
			MAX-ACCESS read-write
			STATUS current
			DESCRIPTION
				"Get the power of blade1."
			::= { blade22 40 }
		
 		b22WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade22 41 }
		
 		b22RealTimePower OBJECT-TYPE
			SYNTAX INTEGER
			MAX-ACCESS read-only
			STATUS current
			DESCRIPTION
				" "
			::= { blade22 43 }
		
 		b22PowerCapping OBJECT-TYPE
			SYNTAX DisplayString
			MAX-ACCESS read-write
			STATUS current
			DESCRIPTION
				" "
			::= { blade22 44 }
		
 		b22Powerreference OBJECT-TYPE
			SYNTAX INTEGER
			MAX-ACCESS read-only
			STATUS current
			DESCRIPTION
				" "
			::= { blade22 45 }
		
 		b22ClearBiosConfig OBJECT-TYPE
			SYNTAX INTEGER
			MAX-ACCESS read-write
			STATUS current
			DESCRIPTION
				" "
			::= { blade22 46 }
		
 		b22BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade22 47 }
		
 		b22BmcUserAdd OBJECT-TYPE
			SYNTAX DisplayString
			MAX-ACCESS read-write
			STATUS current
			DESCRIPTION
				"Used to Add the BMC User
				settable format:
				username,passwd"
			::= { blade22 48 }
		
 		b22BmcUserDel OBJECT-TYPE
			SYNTAX DisplayString
			MAX-ACCESS read-write
			STATUS current
			DESCRIPTION
				"Used to Del the BMC User
				settable format:
				username"
			::= { blade22 49 }
		
 		b22BmcUserPasswd OBJECT-TYPE
			SYNTAX DisplayString
			MAX-ACCESS read-write
			STATUS current
			DESCRIPTION
				"Used to Change the BMC User Passwd
				settable format:
				username,passwd"
			::= { blade22 50 }
		
 		b22BmcUserpropertychg OBJECT-TYPE
			SYNTAX DisplayString
			MAX-ACCESS read-write
			STATUS current
			DESCRIPTION
				"Used to Change the BMC User Property
				settable format:
				username,property"
			::= { blade22 51 }
		
 		b22BmcGateway OBJECT-TYPE
			SYNTAX DisplayString
			MAX-ACCESS read-write
			STATUS current
			DESCRIPTION
				"Read or set the gateway."
			::= { blade22 52 }
		
 		b22SlotBitmap OBJECT-TYPE
			SYNTAX INTEGER
			MAX-ACCESS read-only
			STATUS current
			DESCRIPTION
				" "
			::= { blade22 55 }
		
		b22systemGuid OBJECT-TYPE
			SYNTAX DisplayString
			MAX-ACCESS read-only
			STATUS current
			DESCRIPTION
				" "
			::= { blade22 56 }
		
		b22ProductName OBJECT-TYPE
			SYNTAX DisplayString
			MAX-ACCESS read-only
			STATUS current
			DESCRIPTION
				"display the Version of board12."
			::= { blade22 57 }
		
		b22BundleVersion OBJECT-TYPE
			SYNTAX DisplayString
			MAX-ACCESS read-write
			STATUS current
			DESCRIPTION
				"Get or set the board22 bundle version."
			::= { blade22 58 }

 		blade22SensorTargetTable OBJECT-TYPE
			SYNTAX SEQUENCE OF Blade22SensorTargetEntry
			MAX-ACCESS not-accessible
			STATUS current
			DESCRIPTION
				"A table containing the list of sensor information."
			::= { blade22 2001 }
		
 		blade22SensorTargetEntry OBJECT-TYPE
			SYNTAX Blade22SensorTargetEntry
			MAX-ACCESS not-accessible
			STATUS current
			DESCRIPTION
				"Information about a particular current sensor."
			INDEX { b12Target }
			::= { blade22SensorTargetTable 1 }
		
		Blade22SensorTargetEntry ::=
			SEQUENCE { 
				b22Target
					DisplayString,
				b22Current
					DisplayString,
				b22ThresholdsAll
					DisplayString,
				b22UpperCritical
					DisplayString,
				b22UpperNonCritical
					DisplayString,
				b22UpperNonRecoverable
					DisplayString,
				b22LowerNonCritical
					DisplayString,
				b22LowerCritical
					DisplayString,
				b22LowerNonRecoverable
					DisplayString,
				b22SensorHealth
					INTEGER,
				b22SensorHealthEvents
					DisplayString,
				b22NegativeHysteresis
					DisplayString,
				b22PositiveHysteresis
					DisplayString,
				b22SensorType
					DisplayString,
				b22SensorFRUInfo
					DisplayString
			 }

 		b22Target OBJECT-TYPE
			SYNTAX DisplayString
			MAX-ACCESS not-accessible
			STATUS current
			DESCRIPTION
				"sensor Name"
			::= { blade22SensorTargetEntry 1 }
		
 		b22Current OBJECT-TYPE
			SYNTAX DisplayString
			MAX-ACCESS read-only
			STATUS current
			DESCRIPTION
				"Display the current value of a sensor."
			::= { blade22SensorTargetEntry 2 }
		
 		b22ThresholdsAll OBJECT-TYPE
			SYNTAX DisplayString
			MAX-ACCESS read-only
			STATUS current
			DESCRIPTION
				"All thresholds of a sensor"
			::= { blade22SensorTargetEntry 3 }
		
 		b22UpperCritical OBJECT-TYPE
			SYNTAX DisplayString
			MAX-ACCESS read-write
			STATUS current
			DESCRIPTION
				"Upper critical thresholds"
			::= { blade22SensorTargetEntry 4 }
		
 		b22UpperNonCritical OBJECT-TYPE
			SYNTAX DisplayString
			MAX-ACCESS read-write
			STATUS current
			DESCRIPTION
				"Upper non-critical thresholds"
			::= { blade22SensorTargetEntry 5 }
		
 		b22UpperNonRecoverable OBJECT-TYPE
			SYNTAX DisplayString
			MAX-ACCESS read-write
			STATUS current
			DESCRIPTION
				"Upper non-recoverable thresholds"
			::= { blade22SensorTargetEntry 6 }
		
 		b22LowerNonCritical OBJECT-TYPE
			SYNTAX DisplayString
			MAX-ACCESS read-write
			STATUS current
			DESCRIPTION
				"Lower non-critical thresholds"
			::= { blade22SensorTargetEntry 7 }
		
 		b22LowerCritical OBJECT-TYPE
			SYNTAX DisplayString
			MAX-ACCESS read-write
			STATUS current
			DESCRIPTION
				"Lower critical thresholds"
			::= { blade22SensorTargetEntry 8 }
		
 		b22LowerNonRecoverable OBJECT-TYPE
			SYNTAX DisplayString
			MAX-ACCESS read-write
			STATUS current
			DESCRIPTION
				"Lower non-recoverable thresholds"
			::= { blade22SensorTargetEntry 9 }
		
 		b22SensorHealth OBJECT-TYPE
			SYNTAX INTEGER
				{
				ok(0),
				minor(1),
				major(2),
				critical(3)
				}
			MAX-ACCESS read-only
			STATUS current
			DESCRIPTION
				"b12Health information about a particular b12Location. 
				This will be one of the following:
				(0-ok, 1-minor, 2-major, 3-critical)"
			::= { blade22SensorTargetEntry 10 }
		
 		b22SensorHealthEvents OBJECT-TYPE
			SYNTAX DisplayString
			MAX-ACCESS read-only
			STATUS current
			DESCRIPTION
				"Events that contribute to the b12Health of the b12Location.  
				This is a list of events currently happening on the 
				b12Location."
			::= { blade22SensorTargetEntry 11 }
		
		
 		b22NegativeHysteresis OBJECT-TYPE
			SYNTAX DisplayString
			MAX-ACCESS read-write
			STATUS current
			DESCRIPTION
				"Get/Set the negativeHysteresis value"
			::= { blade22SensorTargetEntry 16 }
		
 		b22PositiveHysteresis OBJECT-TYPE
			SYNTAX DisplayString
			MAX-ACCESS read-write
			STATUS current
			DESCRIPTION
				"Get/Set the positiveHysteresis value."
			::= { blade22SensorTargetEntry 17 }
		
 		b22SensorType OBJECT-TYPE
			SYNTAX DisplayString
			MAX-ACCESS read-only
			STATUS current
			DESCRIPTION
				"Get the type of the sensor."
			::= { blade22SensorTargetEntry 18 }
		
 		b22SensorFRUInfo OBJECT-TYPE
			SYNTAX DisplayString
			MAX-ACCESS read-only
			STATUS current
			DESCRIPTION
				"Get the fruinfo of the sensor."
			::= { blade22SensorTargetEntry 19 }
		
 		blade22FruTable OBJECT-TYPE
			SYNTAX SEQUENCE OF Blade22FruEntry
			MAX-ACCESS not-accessible
			STATUS current
			DESCRIPTION
				"A table containing the list of FRU information."
			::= { blade22 2002 }
		
 		blade22FruEntry OBJECT-TYPE
			SYNTAX Blade22FruEntry
			MAX-ACCESS not-accessible
			STATUS current
			DESCRIPTION
				"Information about a particular current FRU."
			INDEX { b12fruNumber }
			::= { blade22FruTable 1 }
		
		Blade22FruEntry ::=
			SEQUENCE { 
				b22fruNumber
					INTEGER,
				b22FruHotSwapState
					DisplayString,
				b22FruLedProperties
					DisplayString,
				b22FRUControl
					INTEGER,
				b22FRULabel
					DisplayString,
				b22ResetReason
					DisplayString
			 }

 		b22fruNumber OBJECT-TYPE
			SYNTAX INTEGER
			MAX-ACCESS not-accessible
			STATUS current
			DESCRIPTION
				" "
			::= { blade22FruEntry 1 }
		
 		b22FruHotSwapState OBJECT-TYPE
			SYNTAX DisplayString
			MAX-ACCESS read-only
			STATUS current
			DESCRIPTION
				"Retrieve the hot swap state of the FRU from the 
				internally known hot swap states of blade12."
			::= { blade22FruEntry 3 }
		
 		b22FruLedProperties OBJECT-TYPE
			SYNTAX DisplayString
			MAX-ACCESS read-only
			STATUS current
			DESCRIPTION
				"Retrieves the LED support information from a FRU. Returns a comma separated
				list of LEDS and the number of FRU supported user LEDs."
			::= { blade22FruEntry 4 }

		

		b22FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade22FruEntry 9 }
		
 		b22FRULabel OBJECT-TYPE
			SYNTAX DisplayString
			MAX-ACCESS read-only
			STATUS current
			DESCRIPTION
				"Get fru label of blade12."
			::= { blade22FruEntry 10 }
		
 		b22ResetReason OBJECT-TYPE
			SYNTAX DisplayString
			MAX-ACCESS read-only
			STATUS current
			DESCRIPTION
				"Delete fru label of smm."
			::= { blade22FruEntry 11 }
		
 		blade22FruLedTable OBJECT-TYPE
			SYNTAX SEQUENCE OF Blade22FruLedEntry
			MAX-ACCESS not-accessible
			STATUS current
			DESCRIPTION
				"A table containing the list of led information."
			::= { blade22 2003 }
		
 		blade22FruLedEntry OBJECT-TYPE
			SYNTAX Blade22FruLedEntry
			MAX-ACCESS not-accessible
			STATUS current
			DESCRIPTION
				"Information about a particular current led."
			INDEX { b12FruID, b12FruLed }
			::= { blade22FruLedTable 1 }
		
		Blade22FruLedEntry ::=
			SEQUENCE { 
				b22FruID
					INTEGER,
				b22FruLed
					DisplayString,
				b22FruLedColorProps
					DisplayString,
				b22FruLedState
					DisplayString
			 }

 		b22FruID OBJECT-TYPE
			SYNTAX INTEGER
			MAX-ACCESS not-accessible
			STATUS current
			DESCRIPTION
				" "
			::= { blade22FruLedEntry 1 }
		
 		b22FruLed OBJECT-TYPE
			SYNTAX DisplayString
			MAX-ACCESS not-accessible
			STATUS current
			DESCRIPTION
				" "
			::= { blade22FruLedEntry 2 }
		
 		b22FruLedColorProps OBJECT-TYPE
			SYNTAX DisplayString
			MAX-ACCESS read-only
			STATUS current
			DESCRIPTION
				"Finds out what colors are supported by the LED"
			::= { blade22FruLedEntry 3 }
		
 		b22FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade22FruLedEntry 4 }
		
 		blade22FruDescriptionTable OBJECT-TYPE
			SYNTAX SEQUENCE OF Blade22FruDescriptionEntry
			MAX-ACCESS not-accessible
			STATUS current
			DESCRIPTION
				"A table containing the list of blade12 FRU information."
			::= { blade22 2004 }
		
 		blade22FruDescriptionEntry OBJECT-TYPE
			SYNTAX Blade22FruDescriptionEntry
			MAX-ACCESS not-accessible
			STATUS current
			DESCRIPTION
				"Information about a particular current FRU."
			INDEX { b12fruNum }
			::= { blade22FruDescriptionTable 1 }
		
		Blade22FruDescriptionEntry ::=
			SEQUENCE { 
				b22fruNum
					INTEGER,
				b22fruBoardDescription
					DisplayString,
				b22fruBoardManufacturer
					DisplayString,
				b22fruBoardPartNumber
					DisplayString,
				b22fruBoardSerialNumber
					DisplayString,
				b22fruBoardManufactureDate
					DisplayString,
				b22fruProductDescription
					DisplayString,
				b22fruProductManufacturer
					DisplayString,
				b22fruProductPartNumber
					DisplayString,
				b22fruProductSerialNumber
					DisplayString,
				b22fruProductRevision
					DisplayString,
				b22fruAll
					DisplayString
			 }

 		b22fruNum OBJECT-TYPE
			SYNTAX INTEGER
			MAX-ACCESS not-accessible
			STATUS current
			DESCRIPTION
				"blade12 FRU's INDEX"
			::= { blade22FruDescriptionEntry 1 }
		
 		b22fruBoardDescription OBJECT-TYPE
			SYNTAX DisplayString
			MAX-ACCESS read-only
			STATUS current
			DESCRIPTION
				"Used to read the Board Description from the blade12 fru."
			::= { blade22FruDescriptionEntry 2 }
		
 		b22fruBoardManufacturer OBJECT-TYPE
			SYNTAX DisplayString
			MAX-ACCESS read-only
			STATUS current
			DESCRIPTION
				"Used to read the Board Manufacturer from the bladef12 fru."
			::= { blade22FruDescriptionEntry 3 }
		
 		b22fruBoardPartNumber OBJECT-TYPE
			SYNTAX DisplayString
			MAX-ACCESS read-only
			STATUS current
			DESCRIPTION
				"Used to read the Board Part Number from the blade12 fru."
			::= { blade22FruDescriptionEntry 4 }
		
 		b22fruBoardSerialNumber OBJECT-TYPE
			SYNTAX DisplayString
			MAX-ACCESS read-only
			STATUS current
			DESCRIPTION
				"Used to read the Board Serial Number from the blade12 fru."
			::= { blade22FruDescriptionEntry 5 }
		
 		b22fruBoardManufactureDate OBJECT-TYPE
			SYNTAX DisplayString
			MAX-ACCESS read-only
			STATUS current
			DESCRIPTION
				"Used to read the Board Manufacture Date from the blade12 fru."
			::= { blade22FruDescriptionEntry 6 }
		
 		b22fruProductDescription OBJECT-TYPE
			SYNTAX DisplayString
			MAX-ACCESS read-only
			STATUS current
			DESCRIPTION
				"Used to read the Product Description from the blade12 fru."
			::= { blade22FruDescriptionEntry 7 }
		
 		b22fruProductManufacturer OBJECT-TYPE
			SYNTAX DisplayString
			MAX-ACCESS read-only
			STATUS current
			DESCRIPTION
				"Used to read the Product Manufacturer from the blade12 fru."
			::= { blade22FruDescriptionEntry 8 }
		
 		b22fruProductPartNumber OBJECT-TYPE
			SYNTAX DisplayString
			MAX-ACCESS read-only
			STATUS current
			DESCRIPTION
				"Used to read the Product Part Number from the blade12 fru."
			::= { blade22FruDescriptionEntry 9 }
		
 		b22fruProductSerialNumber OBJECT-TYPE
			SYNTAX DisplayString
			MAX-ACCESS read-only
			STATUS current
			DESCRIPTION
				"Used to read the Product Serial Number from the blade12 fru."
			::= { blade22FruDescriptionEntry 10 }
		
 		b22fruProductRevision OBJECT-TYPE
			SYNTAX DisplayString
			MAX-ACCESS read-only
			STATUS current
			DESCRIPTION
				"Used to read the Product Revision from the blade12 fru."
			::= { blade22FruDescriptionEntry 13 }
		
 		b22fruAll OBJECT-TYPE
			SYNTAX DisplayString
			MAX-ACCESS read-only
			STATUS current
			DESCRIPTION
				"Used to read the fru info all."
			::= { blade22FruDescriptionEntry 14 }
		
		blade22CPUTable OBJECT-TYPE
			SYNTAX SEQUENCE OF Blade22CPUEntry
			MAX-ACCESS not-accessible
			STATUS current
			DESCRIPTION
				"A table containing the list of Blade1 FRU information."
			::= { blade22 2006 }
		
		blade22CPUEntry OBJECT-TYPE
			SYNTAX Blade22CPUEntry
			MAX-ACCESS not-accessible
			STATUS current
			DESCRIPTION
				"Information about a particular current FRU."
			INDEX { b22CPUIndex }
			::= { blade22CPUTable 1 }
		
		Blade22CPUEntry ::=
			SEQUENCE { 
				b22CPUIndex
					INTEGER,
				b22CPUMark
					DisplayString,
				b22CPUInfo
					DisplayString,
				b22CPUPresent
					INTEGER,
				b22CPUHealth
					INTEGER,
				b22CPULocation
					DisplayString
			 }

		b22CPUIndex OBJECT-TYPE
			SYNTAX INTEGER
			MAX-ACCESS not-accessible
			STATUS current
			DESCRIPTION
				"CPU INDEX"
			::= { blade22CPUEntry 1 }
		
		b22CPUMark OBJECT-TYPE
			SYNTAX DisplayString
			MAX-ACCESS read-only
			STATUS current
			DESCRIPTION
				"Get the CPU silk-screen."
			::= { blade22CPUEntry 2 }
		
		b22CPUInfo OBJECT-TYPE
			SYNTAX DisplayString
			MAX-ACCESS read-only
			STATUS current
			DESCRIPTION
				"Get the CPU description of vendor, type and frequency."
			::= { blade22CPUEntry 3 }
		
		b22CPUPresent OBJECT-TYPE
			SYNTAX INTEGER
			MAX-ACCESS read-only
			STATUS current
			DESCRIPTION
				"Get the CPU presence status."
			::= { blade22CPUEntry 4 }
		
		b22CPUHealth OBJECT-TYPE
			SYNTAX INTEGER
			MAX-ACCESS read-only
			STATUS current
			DESCRIPTION
				"Get the CPU health status."
			::= { blade22CPUEntry 5 }
		
		b22CPULocation OBJECT-TYPE
			SYNTAX DisplayString
			MAX-ACCESS read-only
			STATUS current
			DESCRIPTION
				"Get the CPU location."
			::= { blade22CPUEntry 6 }
		
		blade22MemoryTable OBJECT-TYPE
			SYNTAX SEQUENCE OF Blade22MemoryEntry
			MAX-ACCESS not-accessible
			STATUS current
			DESCRIPTION
				"A table containing the list of Blade1 FRU information."
			::= { blade22 2007 }
		
		blade22MemoryEntry OBJECT-TYPE
			SYNTAX Blade22MemoryEntry
			MAX-ACCESS not-accessible
			STATUS current
			DESCRIPTION
				"Information about a particular current FRU."
			INDEX { b22MEMIndex }
			::= { blade22MemoryTable 1 }
		
		Blade22MemoryEntry ::=
			SEQUENCE { 
				b22MEMIndex
					INTEGER,
				b22MEMMark
					DisplayString,
				b22MEMInfo
					DisplayString,
				b22MEMPresent
					INTEGER,
				b22MEMHealth
					INTEGER,
				b22MEMLocation
					DisplayString
			 }

		b22MEMIndex OBJECT-TYPE
			SYNTAX INTEGER
			MAX-ACCESS not-accessible
			STATUS current
			DESCRIPTION
				"MEMORY INDEX"
			::= { blade22MemoryEntry 1 }
		
		b22MEMMark OBJECT-TYPE
			SYNTAX DisplayString
			MAX-ACCESS read-only
			STATUS current
			DESCRIPTION
				"Get the memory silk-screen."
			::= { blade22MemoryEntry 2 }
		
		b22MEMInfo OBJECT-TYPE
			SYNTAX DisplayString
			MAX-ACCESS read-only
			STATUS current
			DESCRIPTION
				"Get the memory description of vendor, frequency and capacity."
			::= { blade22MemoryEntry 3 }
		
		b22MEMPresent OBJECT-TYPE
			SYNTAX INTEGER
			MAX-ACCESS read-only
			STATUS current
			DESCRIPTION
				"Get the memory presence status."
			::= { blade22MemoryEntry 4 }
		
		b22MEMHealth OBJECT-TYPE
			SYNTAX INTEGER
			MAX-ACCESS read-only
			STATUS current
			DESCRIPTION
				"Get the memory health status."
			::= { blade22MemoryEntry 5 }
		
		b22MEMLocation OBJECT-TYPE
			SYNTAX DisplayString
			MAX-ACCESS read-only
			STATUS current
			DESCRIPTION
				"Get the memory location."
			::= { blade22MemoryEntry 6 }
		
		blade22MezzTable OBJECT-TYPE
			SYNTAX SEQUENCE OF Blade22MezzEntry
			MAX-ACCESS not-accessible
			STATUS current
			DESCRIPTION
				"A table containing the list of Blade1 FRU information."
			::= { blade22 2008 }
		
		blade22MezzEntry OBJECT-TYPE
			SYNTAX Blade22MezzEntry
			MAX-ACCESS not-accessible
			STATUS current
			DESCRIPTION
				"Information about a particular current FRU."
			INDEX { b22MezzIndex }
			::= { blade22MezzTable 1 }
		
		Blade22MezzEntry ::=
			SEQUENCE { 
				b22MezzIndex
					INTEGER,
				b22MezzMark
					DisplayString,
				b22MezzInfo
					DisplayString,
				b22MezzPresent
					INTEGER,
				b22MezzHealth
					INTEGER,
				b22MezzLocation
					DisplayString,
				b22MezzMac
					DisplayString
			 }

		b22MezzIndex OBJECT-TYPE
			SYNTAX INTEGER
			MAX-ACCESS not-accessible
			STATUS current
			DESCRIPTION
				"MEZZ INDEX"
			::= { blade22MezzEntry 1 }
		
		b22MezzMark OBJECT-TYPE
			SYNTAX DisplayString
			MAX-ACCESS read-only
			STATUS current
			DESCRIPTION
				"Get the MEZZ silk-screen."
			::= { blade22MezzEntry 2 }
		
		b22MezzInfo OBJECT-TYPE
			SYNTAX DisplayString
			MAX-ACCESS read-only
			STATUS current
			DESCRIPTION
				"Get the MEZZ description of type."
			::= { blade22MezzEntry 3 }
		
		b22MezzPresent OBJECT-TYPE
			SYNTAX INTEGER
			MAX-ACCESS read-only
			STATUS current
			DESCRIPTION
				"Get the MEZZ presence status."
			::= { blade22MezzEntry 4 }
		
		b22MezzHealth OBJECT-TYPE
			SYNTAX INTEGER
			MAX-ACCESS read-only
			STATUS current
			DESCRIPTION
				"Get the MEZZ health status."
			::= { blade22MezzEntry 5 }
		
		b22MezzLocation OBJECT-TYPE
			SYNTAX DisplayString
			MAX-ACCESS read-only
			STATUS current
			DESCRIPTION
				"Get the MEZZ location."
			::= { blade22MezzEntry 6 }
		
		b22MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade22MezzEntry 7 }
		
		blade22DiskTable OBJECT-TYPE
			SYNTAX SEQUENCE OF Blade22DiskEntry
			MAX-ACCESS not-accessible
			STATUS current
			DESCRIPTION
				"A table containing the list of Blade1 FRU information."
			::= { blade22 2009 }
		
		blade22DiskEntry OBJECT-TYPE
			SYNTAX Blade22DiskEntry
			MAX-ACCESS not-accessible
			STATUS current
			DESCRIPTION
				"Information about a particular current FRU."
			INDEX { b22DiskIndex }
			::= { blade22DiskTable 1 }
		
		Blade22DiskEntry ::=
			SEQUENCE { 
				b22DiskIndex
					INTEGER,
				b22DiskMark
					DisplayString,
				b22DiskInfo
					DisplayString,
				b22DiskPresent
					INTEGER,
				b22DiskHealth
					INTEGER,
				b22DiskLocation
					DisplayString
			 }

		b22DiskIndex OBJECT-TYPE
			SYNTAX INTEGER
			MAX-ACCESS not-accessible
			STATUS current
			DESCRIPTION
				"DISK INDEX"
			::= { blade22DiskEntry 1 }
		
		b22DiskMark OBJECT-TYPE
			SYNTAX DisplayString
			MAX-ACCESS read-only
			STATUS current
			DESCRIPTION
				"Get the disk silk-screen."
			::= { blade22DiskEntry 2 }
		
		b22DiskInfo OBJECT-TYPE
			SYNTAX DisplayString
			MAX-ACCESS read-only
			STATUS current
			DESCRIPTION
				"Get the disk description of vendor, capacity and speed."
			::= { blade22DiskEntry 3 }
		
		b22DiskPresent OBJECT-TYPE
			SYNTAX INTEGER
			MAX-ACCESS read-only
			STATUS current
			DESCRIPTION
				"Get the disk presence status."
			::= { blade22DiskEntry 4 }
		
		b22DiskHealth OBJECT-TYPE
			SYNTAX INTEGER
			MAX-ACCESS read-only
			STATUS current
			DESCRIPTION
				"Get the disk health status."
			::= { blade22DiskEntry 5 }
		
		b22DiskLocation OBJECT-TYPE
			SYNTAX DisplayString
			MAX-ACCESS read-only
			STATUS current
			DESCRIPTION
				"Get the disk location."
			::= { blade22DiskEntry 6 }
		
		blade22SecretKvmVmmTable OBJECT-TYPE
			SYNTAX SEQUENCE OF Blade22SecretKvmVmmEntry
			MAX-ACCESS not-accessible
			STATUS current
			DESCRIPTION
				"A table containing the list of Blade22 KVM&VMM secret information."
			::= { blade22 2010 }

		blade22SecretKvmVmmEntry OBJECT-TYPE
			SYNTAX Blade22SecretKvmVmmEntry
			MAX-ACCESS not-accessible
			STATUS current
			DESCRIPTION
				"Information about a particular current KVM&VMM."
			INDEX { b22SecretKvmVmmIndex }
			::= { blade22SecretKvmVmmTable 1 }
		Blade22SecretKvmVmmEntry ::=
			SEQUENCE { 
				b22SecretKvmVmmIndex
					INTEGER,
				b22SecretKvmState
					INTEGER,
				b22SecretVmmState
					INTEGER,
				b22MMSecretVmmKey
					DisplayString,
				b22SecretVmmKey
					DisplayString
			 }
		b22SecretKvmVmmIndex OBJECT-TYPE
			SYNTAX INTEGER
			MAX-ACCESS not-accessible
			STATUS current
			DESCRIPTION
				"KVM&VMM INDEX."
			::= { blade22SecretKvmVmmEntry 1 }
		b22SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade22SecretKvmVmmEntry 2 }
		b22SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade22SecretKvmVmmEntry 3 }
		b22MMSecretVmmKey OBJECT-TYPE
			SYNTAX DisplayString
			MAX-ACCESS read-only
			STATUS current
			DESCRIPTION
				"Get the MM secret VMM key."
			::= { blade22SecretKvmVmmEntry 4 }
		b22SecretVmmKey OBJECT-TYPE
			SYNTAX DisplayString
			MAX-ACCESS read-write
			STATUS current
			DESCRIPTION
				"Set the secret VMM key."
			::= { blade22SecretKvmVmmEntry 5 }
		blade23 OBJECT IDENTIFIER ::= { blades 23 }

		
 		b23DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade23 4 }
		
 		b23PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade23 5 }
		
 		b23Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade23 6 }

		
 		b23Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b13Health information about a particular b13Location. 
				This will be one of the following:
				(0-ok, 1-minor, 2-major, 3-majorandminor,4-critical,5-criticalandminor,6-criticalandmajor,7-criticalandmajorandminor)"
			::= { blade23 8 }
		
 		b23HealthEvents OBJECT-TYPE
			SYNTAX DisplayString
			MAX-ACCESS read-only
			STATUS current
			DESCRIPTION
				"Events that contribute to the b13Health of the b13Location.  
				This is a list of events currently happening on the 
				b13Location."
			::= { blade23 9 }
		
 		b23ClearSEL OBJECT-TYPE
			SYNTAX INTEGER { clear(1) }
			MAX-ACCESS read-write
			STATUS current
			DESCRIPTION
				"Clean the BMC's SEL on the board."
			::= { blade23 12 }
		
 		b23ExDiskBoardPresence OBJECT-TYPE
			SYNTAX INTEGER
				{
				not-present(0),
				present(1)
				}
			MAX-ACCESS read-only
			STATUS current
			DESCRIPTION
				"Used to find out if the extended disk board is present.
				0 - not present
				1 - present"
			::= { blade23 14 }
		
 		b23BladeVersion OBJECT-TYPE
			SYNTAX DisplayString
			MAX-ACCESS read-only
			STATUS current
			DESCRIPTION
				"display the Version of board13."
			::= { blade23 20 }
		
 		b23MACAddress OBJECT-TYPE
			SYNTAX DisplayString
			MAX-ACCESS read-only
			STATUS current
			DESCRIPTION
				"display the MACAddress of board13."
			::= { blade23 21 }
		
				
							
		
 		b23Safepwofftime OBJECT-TYPE
			SYNTAX INTEGER
			MAX-ACCESS read-write
			STATUS current
			DESCRIPTION
				"the safe poweroff time.
				"
			::= { blade23 26 }
		
 		b23BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]  
				6=Force boot into BIOS Setup
				15=Force boot from Floppy/primary removable media           
				
				"
			::= { blade23 32 }
		
 		b23Systeminfo OBJECT-TYPE
			SYNTAX DisplayString
			MAX-ACCESS read-write
			STATUS current
			DESCRIPTION
				"display the system information of board13."
			::= { blade23 36 }

		
 		b23SystemProperties OBJECT-TYPE
			SYNTAX DisplayString
			MAX-ACCESS read-only
			STATUS current
			DESCRIPTION
				"Get the power of blade1."
			::= { blade23 39 }
		
 		b23BiosCfg OBJECT-TYPE
			SYNTAX DisplayString
			MAX-ACCESS read-write
			STATUS current
			DESCRIPTION
				"Get the power of blade1."
			::= { blade23 40 }
		
 		b23WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade23 41 }
		
 		b23RealTimePower OBJECT-TYPE
			SYNTAX INTEGER
			MAX-ACCESS read-only
			STATUS current
			DESCRIPTION
				" "
			::= { blade23 43 }
		
 		b23PowerCapping OBJECT-TYPE
			SYNTAX DisplayString
			MAX-ACCESS read-write
			STATUS current
			DESCRIPTION
				" "
			::= { blade23 44 }
		
 		b23Powerreference OBJECT-TYPE
			SYNTAX INTEGER
			MAX-ACCESS read-only
			STATUS current
			DESCRIPTION
				" "
			::= { blade23 45 }
		
 		b23ClearBiosConfig OBJECT-TYPE
			SYNTAX INTEGER
			MAX-ACCESS read-write
			STATUS current
			DESCRIPTION
				" "
			::= { blade23 46 }
		
 		b23BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade23 47 }
		
 		b23BmcUserAdd OBJECT-TYPE
			SYNTAX DisplayString
			MAX-ACCESS read-write
			STATUS current
			DESCRIPTION
				"Used to Add the BMC User
				settable format:
				username,passwd"
			::= { blade23 48 }
		
 		b23BmcUserDel OBJECT-TYPE
			SYNTAX DisplayString
			MAX-ACCESS read-write
			STATUS current
			DESCRIPTION
				"Used to Del the BMC User
				settable format:
				username"
			::= { blade23 49 }
		
 		b23BmcUserPasswd OBJECT-TYPE
			SYNTAX DisplayString
			MAX-ACCESS read-write
			STATUS current
			DESCRIPTION
				"Used to Change the BMC User Passwd
				settable format:
				username,passwd"
			::= { blade23 50 }
		
 		b23BmcUserpropertychg OBJECT-TYPE
			SYNTAX DisplayString
			MAX-ACCESS read-write
			STATUS current
			DESCRIPTION
				"Used to Change the BMC User Property
				settable format:
				username,property"
			::= { blade23 51 }
		
 		b23BmcGateway OBJECT-TYPE
			SYNTAX DisplayString
			MAX-ACCESS read-write
			STATUS current
			DESCRIPTION
				"Read or set the gateway."
			::= { blade23 52 }
		
 		b23SlotBitmap OBJECT-TYPE
			SYNTAX INTEGER
			MAX-ACCESS read-only
			STATUS current
			DESCRIPTION
				" "
			::= { blade23 55 }
		
		b23systemGuid OBJECT-TYPE
			SYNTAX DisplayString
			MAX-ACCESS read-only
			STATUS current
			DESCRIPTION
				" "
			::= { blade23 56 }
		
		b23ProductName OBJECT-TYPE
			SYNTAX DisplayString
			MAX-ACCESS read-only
			STATUS current
			DESCRIPTION
				"display the Version of board13."
			::= { blade23 57 }
		
		b23BundleVersion OBJECT-TYPE
			SYNTAX DisplayString
			MAX-ACCESS read-write
			STATUS current
			DESCRIPTION
				"Get or set the board23 bundle version."
			::= { blade23 58 }

 		blade23SensorTargetTable OBJECT-TYPE
			SYNTAX SEQUENCE OF Blade23SensorTargetEntry
			MAX-ACCESS not-accessible
			STATUS current
			DESCRIPTION
				"A table containing the list of sensor information."
			::= { blade23 2001 }
		
 		blade23SensorTargetEntry OBJECT-TYPE
			SYNTAX Blade23SensorTargetEntry
			MAX-ACCESS not-accessible
			STATUS current
			DESCRIPTION
				"Information about a particular current sensor."
			INDEX { b13Target }
			::= { blade23SensorTargetTable 1 }
		
		Blade23SensorTargetEntry ::=
			SEQUENCE { 
				b23Target
					DisplayString,
				b23Current
					DisplayString,
				b23ThresholdsAll
					DisplayString,
				b23UpperCritical
					DisplayString,
				b23UpperNonCritical
					DisplayString,
				b23UpperNonRecoverable
					DisplayString,
				b23LowerNonCritical
					DisplayString,
				b23LowerCritical
					DisplayString,
				b23LowerNonRecoverable
					DisplayString,
				b23SensorHealth
					INTEGER,
				b23SensorHealthEvents
					DisplayString,
				b23NegativeHysteresis
					DisplayString,
				b23PositiveHysteresis
					DisplayString,
				b23SensorType
					DisplayString,
				b23SensorFRUInfo
					DisplayString
			 }

 		b23Target OBJECT-TYPE
			SYNTAX DisplayString
			MAX-ACCESS not-accessible
			STATUS current
			DESCRIPTION
				"sensor Name"
			::= { blade23SensorTargetEntry 1 }
		
 		b23Current OBJECT-TYPE
			SYNTAX DisplayString
			MAX-ACCESS read-only
			STATUS current
			DESCRIPTION
				"Display the current value of a sensor."
			::= { blade23SensorTargetEntry 2 }
		
 		b23ThresholdsAll OBJECT-TYPE
			SYNTAX DisplayString
			MAX-ACCESS read-only
			STATUS current
			DESCRIPTION
				"All thresholds of a sensor"
			::= { blade23SensorTargetEntry 3 }
		
 		b23UpperCritical OBJECT-TYPE
			SYNTAX DisplayString
			MAX-ACCESS read-write
			STATUS current
			DESCRIPTION
				"Upper critical thresholds"
			::= { blade23SensorTargetEntry 4 }
		
 		b23UpperNonCritical OBJECT-TYPE
			SYNTAX DisplayString
			MAX-ACCESS read-write
			STATUS current
			DESCRIPTION
				"Upper non-critical thresholds"
			::= { blade23SensorTargetEntry 5 }
		
 		b23UpperNonRecoverable OBJECT-TYPE
			SYNTAX DisplayString
			MAX-ACCESS read-write
			STATUS current
			DESCRIPTION
				"Upper non-recoverable thresholds"
			::= { blade23SensorTargetEntry 6 }
		
 		b23LowerNonCritical OBJECT-TYPE
			SYNTAX DisplayString
			MAX-ACCESS read-write
			STATUS current
			DESCRIPTION
				"Lower non-critical thresholds"
			::= { blade23SensorTargetEntry 7 }
		
 		b23LowerCritical OBJECT-TYPE
			SYNTAX DisplayString
			MAX-ACCESS read-write
			STATUS current
			DESCRIPTION
				"Lower critical thresholds"
			::= { blade23SensorTargetEntry 8 }
		
 		b23LowerNonRecoverable OBJECT-TYPE
			SYNTAX DisplayString
			MAX-ACCESS read-write
			STATUS current
			DESCRIPTION
				"Lower non-recoverable thresholds"
			::= { blade23SensorTargetEntry 9 }
		
 		b23SensorHealth OBJECT-TYPE
			SYNTAX INTEGER
				{
				ok(0),
				minor(1),
				major(2),
				critical(3)
				}
			MAX-ACCESS read-only
			STATUS current
			DESCRIPTION
				"b13Health information about a particular b13Location. 
				This will be one of the following:
				(0-ok, 1-minor, 2-major, 3-critical)"
			::= { blade23SensorTargetEntry 10 }
		
 		b23SensorHealthEvents OBJECT-TYPE
			SYNTAX DisplayString
			MAX-ACCESS read-only
			STATUS current
			DESCRIPTION
				"Events that contribute to the b13Health of the b13Location.  
				This is a list of events currently happening on the 
				b13Location."
			::= { blade23SensorTargetEntry 11 }
		
		
 		b23NegativeHysteresis OBJECT-TYPE
			SYNTAX DisplayString
			MAX-ACCESS read-write
			STATUS current
			DESCRIPTION
				"Get/Set the negativeHysteresis value"
			::= { blade23SensorTargetEntry 16 }
		
 		b23PositiveHysteresis OBJECT-TYPE
			SYNTAX DisplayString
			MAX-ACCESS read-write
			STATUS current
			DESCRIPTION
				"Get/Set the positiveHysteresis value."
			::= { blade23SensorTargetEntry 17 }
		
 		b23SensorType OBJECT-TYPE
			SYNTAX DisplayString
			MAX-ACCESS read-only
			STATUS current
			DESCRIPTION
				"Get the type of the sensor."
			::= { blade23SensorTargetEntry 18 }
		
 		b23SensorFRUInfo OBJECT-TYPE
			SYNTAX DisplayString
			MAX-ACCESS read-only
			STATUS current
			DESCRIPTION
				"Get the fruinfo of the sensor."
			::= { blade23SensorTargetEntry 19 }
		
 		blade23FruTable OBJECT-TYPE
			SYNTAX SEQUENCE OF Blade23FruEntry
			MAX-ACCESS not-accessible
			STATUS current
			DESCRIPTION
				"A table containing the list of FRU information."
			::= { blade23 2002 }
		
 		blade23FruEntry OBJECT-TYPE
			SYNTAX Blade23FruEntry
			MAX-ACCESS not-accessible
			STATUS current
			DESCRIPTION
				"Information about a particular current FRU."
			INDEX { b13fruNumber }
			::= { blade23FruTable 1 }
		
		Blade23FruEntry ::=
			SEQUENCE { 
				b23fruNumber
					INTEGER,
				b23FruHotSwapState
					DisplayString,
				b23FruLedProperties
					DisplayString,
				b23FRUControl
					INTEGER,
				b23FRULabel
					DisplayString,
				b23ResetReason
					DisplayString
			 }

 		b23fruNumber OBJECT-TYPE
			SYNTAX INTEGER
			MAX-ACCESS not-accessible
			STATUS current
			DESCRIPTION
				" "
			::= { blade23FruEntry 1 }
		
 		b23FruHotSwapState OBJECT-TYPE
			SYNTAX DisplayString
			MAX-ACCESS read-only
			STATUS current
			DESCRIPTION
				"Retrieve the hot swap state of the FRU from the 
				internally known hot swap states of blade13."
			::= { blade23FruEntry 3 }
		
 		b23FruLedProperties OBJECT-TYPE
			SYNTAX DisplayString
			MAX-ACCESS read-only
			STATUS current
			DESCRIPTION
				"Retrieves the LED support information from a FRU. Returns a comma separated
				list of LEDS and the number of FRU supported user LEDs."
			::= { blade23FruEntry 4 }

		

		b23FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade23FruEntry 9 }
		
 		b23FRULabel OBJECT-TYPE
			SYNTAX DisplayString
			MAX-ACCESS read-only
			STATUS current
			DESCRIPTION
				"Get fru label of blade13."
			::= { blade23FruEntry 10 }
		
 		b23ResetReason OBJECT-TYPE
			SYNTAX DisplayString
			MAX-ACCESS read-only
			STATUS current
			DESCRIPTION
				"Delete fru label of smm."
			::= { blade23FruEntry 11 }
		
 		blade23FruLedTable OBJECT-TYPE
			SYNTAX SEQUENCE OF Blade23FruLedEntry
			MAX-ACCESS not-accessible
			STATUS current
			DESCRIPTION
				"A table containing the list of led information."
			::= { blade23 2003 }
		
 		blade23FruLedEntry OBJECT-TYPE
			SYNTAX Blade23FruLedEntry
			MAX-ACCESS not-accessible
			STATUS current
			DESCRIPTION
				"Information about a particular current led."
			INDEX { b13FruID, b13FruLed }
			::= { blade23FruLedTable 1 }
		
		Blade23FruLedEntry ::=
			SEQUENCE { 
				b23FruID
					INTEGER,
				b23FruLed
					DisplayString,
				b23FruLedColorProps
					DisplayString,
				b23FruLedState
					DisplayString
			 }

 		b23FruID OBJECT-TYPE
			SYNTAX INTEGER
			MAX-ACCESS not-accessible
			STATUS current
			DESCRIPTION
				" "
			::= { blade23FruLedEntry 1 }
		
 		b23FruLed OBJECT-TYPE
			SYNTAX DisplayString
			MAX-ACCESS not-accessible
			STATUS current
			DESCRIPTION
				" "
			::= { blade23FruLedEntry 2 }
		
 		b23FruLedColorProps OBJECT-TYPE
			SYNTAX DisplayString
			MAX-ACCESS read-only
			STATUS current
			DESCRIPTION
				"Finds out what colors are supported by the LED"
			::= { blade23FruLedEntry 3 }
		
 		b23FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade23FruLedEntry 4 }
		
 		blade23FruDescriptionTable OBJECT-TYPE
			SYNTAX SEQUENCE OF Blade23FruDescriptionEntry
			MAX-ACCESS not-accessible
			STATUS current
			DESCRIPTION
				"A table containing the list of blade13 FRU information."
			::= { blade23 2004 }
		
 		blade23FruDescriptionEntry OBJECT-TYPE
			SYNTAX Blade23FruDescriptionEntry
			MAX-ACCESS not-accessible
			STATUS current
			DESCRIPTION
				"Information about a particular current FRU."
			INDEX { b13fruNum }
			::= { blade23FruDescriptionTable 1 }
		
		Blade23FruDescriptionEntry ::=
			SEQUENCE { 
				b23fruNum
					INTEGER,
				b23fruBoardDescription
					DisplayString,
				b23fruBoardManufacturer
					DisplayString,
				b23fruBoardPartNumber
					DisplayString,
				b23fruBoardSerialNumber
					DisplayString,
				b23fruBoardManufactureDate
					DisplayString,
				b23fruProductDescription
					DisplayString,
				b23fruProductManufacturer
					DisplayString,
				b23fruProductPartNumber
					DisplayString,
				b23fruProductSerialNumber
					DisplayString,
				b23fruProductRevision
					DisplayString,
				b23fruAll
					DisplayString
			 }

 		b23fruNum OBJECT-TYPE
			SYNTAX INTEGER
			MAX-ACCESS not-accessible
			STATUS current
			DESCRIPTION
				"blade13 FRU's INDEX"
			::= { blade23FruDescriptionEntry 1 }
		
 		b23fruBoardDescription OBJECT-TYPE
			SYNTAX DisplayString
			MAX-ACCESS read-only
			STATUS current
			DESCRIPTION
				"Used to read the Board Description from the blade13 fru."
			::= { blade23FruDescriptionEntry 2 }
		
 		b23fruBoardManufacturer OBJECT-TYPE
			SYNTAX DisplayString
			MAX-ACCESS read-only
			STATUS current
			DESCRIPTION
				"Used to read the Board Manufacturer from the bladef13 fru."
			::= { blade23FruDescriptionEntry 3 }
		
 		b23fruBoardPartNumber OBJECT-TYPE
			SYNTAX DisplayString
			MAX-ACCESS read-only
			STATUS current
			DESCRIPTION
				"Used to read the Board Part Number from the blade13 fru."
			::= { blade23FruDescriptionEntry 4 }
		
 		b23fruBoardSerialNumber OBJECT-TYPE
			SYNTAX DisplayString
			MAX-ACCESS read-only
			STATUS current
			DESCRIPTION
				"Used to read the Board Serial Number from the blade13 fru."
			::= { blade23FruDescriptionEntry 5 }
		
 		b23fruBoardManufactureDate OBJECT-TYPE
			SYNTAX DisplayString
			MAX-ACCESS read-only
			STATUS current
			DESCRIPTION
				"Used to read the Board Manufacture Date from the blade13 fru."
			::= { blade23FruDescriptionEntry 6 }
		
 		b23fruProductDescription OBJECT-TYPE
			SYNTAX DisplayString
			MAX-ACCESS read-only
			STATUS current
			DESCRIPTION
				"Used to read the Product Description from the blade13 fru."
			::= { blade23FruDescriptionEntry 7 }
		
 		b23fruProductManufacturer OBJECT-TYPE
			SYNTAX DisplayString
			MAX-ACCESS read-only
			STATUS current
			DESCRIPTION
				"Used to read the Product Manufacturer from the blade13 fru."
			::= { blade23FruDescriptionEntry 8 }
		
 		b23fruProductPartNumber OBJECT-TYPE
			SYNTAX DisplayString
			MAX-ACCESS read-only
			STATUS current
			DESCRIPTION
				"Used to read the Product Part Number from the blade13 fru."
			::= { blade23FruDescriptionEntry 9 }
		
 		b23fruProductSerialNumber OBJECT-TYPE
			SYNTAX DisplayString
			MAX-ACCESS read-only
			STATUS current
			DESCRIPTION
				"Used to read the Product Serial Number from the blade13 fru."
			::= { blade23FruDescriptionEntry 10 }
		
 		b23fruProductRevision OBJECT-TYPE
			SYNTAX DisplayString
			MAX-ACCESS read-only
			STATUS current
			DESCRIPTION
				"Used to read the Product Revision from the blade13 fru."
			::= { blade23FruDescriptionEntry 13 }
		
 		b23fruAll OBJECT-TYPE
			SYNTAX DisplayString
			MAX-ACCESS read-only
			STATUS current
			DESCRIPTION
				"Used to read the fru info all."
			::= { blade23FruDescriptionEntry 14 }
		
		blade23CPUTable OBJECT-TYPE
			SYNTAX SEQUENCE OF Blade23CPUEntry
			MAX-ACCESS not-accessible
			STATUS current
			DESCRIPTION
				"A table containing the list of Blade1 FRU information."
			::= { blade23 2006 }
		
		blade23CPUEntry OBJECT-TYPE
			SYNTAX Blade23CPUEntry
			MAX-ACCESS not-accessible
			STATUS current
			DESCRIPTION
				"Information about a particular current FRU."
			INDEX { b23CPUIndex }
			::= { blade23CPUTable 1 }
		
		Blade23CPUEntry ::=
			SEQUENCE { 
				b23CPUIndex
					INTEGER,
				b23CPUMark
					DisplayString,
				b23CPUInfo
					DisplayString,
				b23CPUPresent
					INTEGER,
				b23CPUHealth
					INTEGER,
				b23CPULocation
					DisplayString
			 }

		b23CPUIndex OBJECT-TYPE
			SYNTAX INTEGER
			MAX-ACCESS not-accessible
			STATUS current
			DESCRIPTION
				"CPU INDEX"
			::= { blade23CPUEntry 1 }
		
		b23CPUMark OBJECT-TYPE
			SYNTAX DisplayString
			MAX-ACCESS read-only
			STATUS current
			DESCRIPTION
				"Get the CPU silk-screen."
			::= { blade23CPUEntry 2 }
		
		b23CPUInfo OBJECT-TYPE
			SYNTAX DisplayString
			MAX-ACCESS read-only
			STATUS current
			DESCRIPTION
				"Get the CPU description of vendor, type and frequency."
			::= { blade23CPUEntry 3 }
		
		b23CPUPresent OBJECT-TYPE
			SYNTAX INTEGER
			MAX-ACCESS read-only
			STATUS current
			DESCRIPTION
				"Get the CPU presence status."
			::= { blade23CPUEntry 4 }
		
		b23CPUHealth OBJECT-TYPE
			SYNTAX INTEGER
			MAX-ACCESS read-only
			STATUS current
			DESCRIPTION
				"Get the CPU health status."
			::= { blade23CPUEntry 5 }
		
		b23CPULocation OBJECT-TYPE
			SYNTAX DisplayString
			MAX-ACCESS read-only
			STATUS current
			DESCRIPTION
				"Get the CPU location."
			::= { blade23CPUEntry 6 }
		
		blade23MemoryTable OBJECT-TYPE
			SYNTAX SEQUENCE OF Blade23MemoryEntry
			MAX-ACCESS not-accessible
			STATUS current
			DESCRIPTION
				"A table containing the list of Blade1 FRU information."
			::= { blade23 2007 }
		
		blade23MemoryEntry OBJECT-TYPE
			SYNTAX Blade23MemoryEntry
			MAX-ACCESS not-accessible
			STATUS current
			DESCRIPTION
				"Information about a particular current FRU."
			INDEX { b23MEMIndex }
			::= { blade23MemoryTable 1 }
		
		Blade23MemoryEntry ::=
			SEQUENCE { 
				b23MEMIndex
					INTEGER,
				b23MEMMark
					DisplayString,
				b23MEMInfo
					DisplayString,
				b23MEMPresent
					INTEGER,
				b23MEMHealth
					INTEGER,
				b23MEMLocation
					DisplayString
			 }

		b23MEMIndex OBJECT-TYPE
			SYNTAX INTEGER
			MAX-ACCESS not-accessible
			STATUS current
			DESCRIPTION
				"MEMORY INDEX"
			::= { blade23MemoryEntry 1 }
		
		b23MEMMark OBJECT-TYPE
			SYNTAX DisplayString
			MAX-ACCESS read-only
			STATUS current
			DESCRIPTION
				"Get the memory silk-screen."
			::= { blade23MemoryEntry 2 }
		
		b23MEMInfo OBJECT-TYPE
			SYNTAX DisplayString
			MAX-ACCESS read-only
			STATUS current
			DESCRIPTION
				"Get the memory description of vendor, frequency and capacity."
			::= { blade23MemoryEntry 3 }
		
		b23MEMPresent OBJECT-TYPE
			SYNTAX INTEGER
			MAX-ACCESS read-only
			STATUS current
			DESCRIPTION
				"Get the memory presence status."
			::= { blade23MemoryEntry 4 }
		
		b23MEMHealth OBJECT-TYPE
			SYNTAX INTEGER
			MAX-ACCESS read-only
			STATUS current
			DESCRIPTION
				"Get the memory health status."
			::= { blade23MemoryEntry 5 }
		
		b23MEMLocation OBJECT-TYPE
			SYNTAX DisplayString
			MAX-ACCESS read-only
			STATUS current
			DESCRIPTION
				"Get the memory location."
			::= { blade23MemoryEntry 6 }
		
		blade23MezzTable OBJECT-TYPE
			SYNTAX SEQUENCE OF Blade23MezzEntry
			MAX-ACCESS not-accessible
			STATUS current
			DESCRIPTION
				"A table containing the list of Blade1 FRU information."
			::= { blade23 2008 }
		
		blade23MezzEntry OBJECT-TYPE
			SYNTAX Blade23MezzEntry
			MAX-ACCESS not-accessible
			STATUS current
			DESCRIPTION
				"Information about a particular current FRU."
			INDEX { b23MezzIndex }
			::= { blade23MezzTable 1 }
		
		Blade23MezzEntry ::=
			SEQUENCE { 
				b23MezzIndex
					INTEGER,
				b23MezzMark
					DisplayString,
				b23MezzInfo
					DisplayString,
				b23MezzPresent
					INTEGER,
				b23MezzHealth
					INTEGER,
				b23MezzLocation
					DisplayString,
				b23MezzMac
					DisplayString
			 }

		b23MezzIndex OBJECT-TYPE
			SYNTAX INTEGER
			MAX-ACCESS not-accessible
			STATUS current
			DESCRIPTION
				"MEZZ INDEX"
			::= { blade23MezzEntry 1 }
		
		b23MezzMark OBJECT-TYPE
			SYNTAX DisplayString
			MAX-ACCESS read-only
			STATUS current
			DESCRIPTION
				"Get the MEZZ silk-screen."
			::= { blade23MezzEntry 2 }
		
		b23MezzInfo OBJECT-TYPE
			SYNTAX DisplayString
			MAX-ACCESS read-only
			STATUS current
			DESCRIPTION
				"Get the MEZZ description of type."
			::= { blade23MezzEntry 3 }
		
		b23MezzPresent OBJECT-TYPE
			SYNTAX INTEGER
			MAX-ACCESS read-only
			STATUS current
			DESCRIPTION
				"Get the MEZZ presence status."
			::= { blade23MezzEntry 4 }
		
		b23MezzHealth OBJECT-TYPE
			SYNTAX INTEGER
			MAX-ACCESS read-only
			STATUS current
			DESCRIPTION
				"Get the MEZZ health status."
			::= { blade23MezzEntry 5 }
		
		b23MezzLocation OBJECT-TYPE
			SYNTAX DisplayString
			MAX-ACCESS read-only
			STATUS current
			DESCRIPTION
				"Get the MEZZ location."
			::= { blade23MezzEntry 6 }
		
		b23MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade23MezzEntry 7 }
		
		blade23DiskTable OBJECT-TYPE
			SYNTAX SEQUENCE OF Blade23DiskEntry
			MAX-ACCESS not-accessible
			STATUS current
			DESCRIPTION
				"A table containing the list of Blade1 FRU information."
			::= { blade23 2009 }
		
		blade23DiskEntry OBJECT-TYPE
			SYNTAX Blade23DiskEntry
			MAX-ACCESS not-accessible
			STATUS current
			DESCRIPTION
				"Information about a particular current FRU."
			INDEX { b23DiskIndex }
			::= { blade23DiskTable 1 }
		
		Blade23DiskEntry ::=
			SEQUENCE { 
				b23DiskIndex
					INTEGER,
				b23DiskMark
					DisplayString,
				b23DiskInfo
					DisplayString,
				b23DiskPresent
					INTEGER,
				b23DiskHealth
					INTEGER,
				b23DiskLocation
					DisplayString
			 }

		b23DiskIndex OBJECT-TYPE
			SYNTAX INTEGER
			MAX-ACCESS not-accessible
			STATUS current
			DESCRIPTION
				"DISK INDEX"
			::= { blade23DiskEntry 1 }
		
		b23DiskMark OBJECT-TYPE
			SYNTAX DisplayString
			MAX-ACCESS read-only
			STATUS current
			DESCRIPTION
				"Get the disk silk-screen."
			::= { blade23DiskEntry 2 }
		
		b23DiskInfo OBJECT-TYPE
			SYNTAX DisplayString
			MAX-ACCESS read-only
			STATUS current
			DESCRIPTION
				"Get the disk description of vendor, capacity and speed."
			::= { blade23DiskEntry 3 }
		
		b23DiskPresent OBJECT-TYPE
			SYNTAX INTEGER
			MAX-ACCESS read-only
			STATUS current
			DESCRIPTION
				"Get the disk presence status."
			::= { blade23DiskEntry 4 }
		
		b23DiskHealth OBJECT-TYPE
			SYNTAX INTEGER
			MAX-ACCESS read-only
			STATUS current
			DESCRIPTION
				"Get the disk health status."
			::= { blade23DiskEntry 5 }
		
		b23DiskLocation OBJECT-TYPE
			SYNTAX DisplayString
			MAX-ACCESS read-only
			STATUS current
			DESCRIPTION
				"Get the disk location."
			::= { blade23DiskEntry 6 }
		
		blade23SecretKvmVmmTable OBJECT-TYPE
			SYNTAX SEQUENCE OF Blade23SecretKvmVmmEntry
			MAX-ACCESS not-accessible
			STATUS current
			DESCRIPTION
				"A table containing the list of Blade23 KVM&VMM secret information."
			::= { blade23 2010 }

		blade23SecretKvmVmmEntry OBJECT-TYPE
			SYNTAX Blade23SecretKvmVmmEntry
			MAX-ACCESS not-accessible
			STATUS current
			DESCRIPTION
				"Information about a particular current KVM&VMM."
			INDEX { b23SecretKvmVmmIndex }
			::= { blade23SecretKvmVmmTable 1 }
		Blade23SecretKvmVmmEntry ::=
			SEQUENCE { 
				b23SecretKvmVmmIndex
					INTEGER,
				b23SecretKvmState
					INTEGER,
				b23SecretVmmState
					INTEGER,
				b23MMSecretVmmKey
					DisplayString,
				b23SecretVmmKey
					DisplayString
			 }
		b23SecretKvmVmmIndex OBJECT-TYPE
			SYNTAX INTEGER
			MAX-ACCESS not-accessible
			STATUS current
			DESCRIPTION
				"KVM&VMM INDEX."
			::= { blade23SecretKvmVmmEntry 1 }
		b23SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade23SecretKvmVmmEntry 2 }
		b23SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade23SecretKvmVmmEntry 3 }
		b23MMSecretVmmKey OBJECT-TYPE
			SYNTAX DisplayString
			MAX-ACCESS read-only
			STATUS current
			DESCRIPTION
				"Get the MM secret VMM key."
			::= { blade23SecretKvmVmmEntry 4 }
		b23SecretVmmKey OBJECT-TYPE
			SYNTAX DisplayString
			MAX-ACCESS read-write
			STATUS current
			DESCRIPTION
				"Set the secret VMM key."
			::= { blade23SecretKvmVmmEntry 5 }
		blade24 OBJECT IDENTIFIER ::= { blades 24 }

		
 		b24DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade24 4 }
		
 		b24PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade24 5 }
		
 		b24Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade24 6 }

		
 		b24Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade24 8 }
		
 		b24HealthEvents OBJECT-TYPE
			SYNTAX DisplayString
			MAX-ACCESS read-only
			STATUS current
			DESCRIPTION
				"Events that contribute to the b14Health of the b14Location.  
				This is a list of events currently happening on the 
				b14Location."
			::= { blade24 9 }
		
		b24ClearSEL OBJECT-TYPE
			SYNTAX INTEGER { clear(1) }
			MAX-ACCESS read-write
			STATUS current
			DESCRIPTION
				"Clean the BMC's SEL on the board."
			::= { blade24 12 }
		
 		b24ExDiskBoardPresence OBJECT-TYPE
			SYNTAX INTEGER
				{
				not-present(0),
				present(1)
				}
			MAX-ACCESS read-only
			STATUS current
			DESCRIPTION
				"Used to find out if the extended disk board is present.
				0 - not present
				1 - present"
			::= { blade24 14 }
		
 		b24BladeVersion OBJECT-TYPE
			SYNTAX DisplayString
			MAX-ACCESS read-only
			STATUS current
			DESCRIPTION
				"display the Version of board14."
			::= { blade24 20 }
		
 		b24MACAddress OBJECT-TYPE
			SYNTAX DisplayString
			MAX-ACCESS read-only
			STATUS current
			DESCRIPTION
				"display the MACAddress of board14."
			::= { blade24 21 }
		
				
							
		
 		b24Safepwofftime OBJECT-TYPE
			SYNTAX INTEGER
			MAX-ACCESS read-write
			STATUS current
			DESCRIPTION
				"the safe poweroff time.
				"
			::= { blade24 26 }
		
 		b24BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]   
				6=Force boot into BIOS Setup
				15=Force boot from Floppy/primary removable media           
				
				"
			::= { blade24 32 }
		
 		b24Systeminfo OBJECT-TYPE
			SYNTAX DisplayString
			MAX-ACCESS read-write
			STATUS current
			DESCRIPTION
				"display the system information of board14."
			::= { blade24 36 }

		
 		b24SystemProperties OBJECT-TYPE
			SYNTAX DisplayString
			MAX-ACCESS read-only
			STATUS current
			DESCRIPTION
				"Get the power of blade1."
			::= { blade24 39 }
		
 		b24BiosCfg OBJECT-TYPE
			SYNTAX DisplayString
			MAX-ACCESS read-write
			STATUS current
			DESCRIPTION
				"Get the power of blade1."
			::= { blade24 40 }
		
 		b24WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade24 41 }
		
 		b24RealTimePower OBJECT-TYPE
			SYNTAX INTEGER
			MAX-ACCESS read-only
			STATUS current
			DESCRIPTION
				" "
			::= { blade24 43 }
		
 		b24PowerCapping OBJECT-TYPE
			SYNTAX DisplayString
			MAX-ACCESS read-write
			STATUS current
			DESCRIPTION
				" "
			::= { blade24 44 }
		
 		b24Powerreference OBJECT-TYPE
			SYNTAX INTEGER
			MAX-ACCESS read-only
			STATUS current
			DESCRIPTION
				" "
			::= { blade24 45 }
		
 		b24ClearBiosConfig OBJECT-TYPE
			SYNTAX INTEGER
			MAX-ACCESS read-write
			STATUS current
			DESCRIPTION
				" "
			::= { blade24 46 }
		
 		b24BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade24 47 }
		
 		b24BmcUserAdd OBJECT-TYPE
			SYNTAX DisplayString
			MAX-ACCESS read-write
			STATUS current
			DESCRIPTION
				"Used to Add the BMC User
				settable format:
				username,passwd"
			::= { blade24 48 }
		
 		b24BmcUserDel OBJECT-TYPE
			SYNTAX DisplayString
			MAX-ACCESS read-write
			STATUS current
			DESCRIPTION
				"Used to Del the BMC User
				settable format:
				username"
			::= { blade24 49 }
		
 		b24BmcUserPasswd OBJECT-TYPE
			SYNTAX DisplayString
			MAX-ACCESS read-write
			STATUS current
			DESCRIPTION
				"Used to Change the BMC User Passwd
				settable format:
				username,passwd"
			::= { blade24 50 }
		
 		b24BmcUserpropertychg OBJECT-TYPE
			SYNTAX DisplayString
			MAX-ACCESS read-write
			STATUS current
			DESCRIPTION
				"Used to Change the BMC User Property
				settable format:
				username,property"
			::= { blade24 51 }
		
 		b24BmcGateway OBJECT-TYPE
			SYNTAX DisplayString
			MAX-ACCESS read-write
			STATUS current
			DESCRIPTION
				"Read or set the gateway."
			::= { blade24 52 }
		
 		b24SlotBitmap OBJECT-TYPE
			SYNTAX INTEGER
			MAX-ACCESS read-only
			STATUS current
			DESCRIPTION
				" "
			::= { blade24 55 }
		
		b24systemGuid OBJECT-TYPE
			SYNTAX DisplayString
			MAX-ACCESS read-only
			STATUS current
			DESCRIPTION
				" "
			::= { blade24 56 }
		
		b24ProductName OBJECT-TYPE
			SYNTAX DisplayString
			MAX-ACCESS read-only
			STATUS current
			DESCRIPTION
				"display the Version of board14."
			::= { blade24 57 }
		
		b24BundleVersion OBJECT-TYPE
			SYNTAX DisplayString
			MAX-ACCESS read-write
			STATUS current
			DESCRIPTION
				"Get or set the board24 bundle version."
			::= { blade24 58 }

 		blade24SensorTargetTable OBJECT-TYPE
			SYNTAX SEQUENCE OF Blade24SensorTargetEntry
			MAX-ACCESS not-accessible
			STATUS current
			DESCRIPTION
				"A table containing the list of sensor information."
			::= { blade24 2001 }
		
 		blade24SensorTargetEntry OBJECT-TYPE
			SYNTAX Blade24SensorTargetEntry
			MAX-ACCESS not-accessible
			STATUS current
			DESCRIPTION
				"Information about a particular current sensor."
			INDEX { b14Target }
			::= { blade24SensorTargetTable 1 }
		
		Blade24SensorTargetEntry ::=
			SEQUENCE { 
				b24Target
					DisplayString,
				b24Current
					DisplayString,
				b24ThresholdsAll
					DisplayString,
				b24UpperCritical
					DisplayString,
				b24UpperNonCritical
					DisplayString,
				b24UpperNonRecoverable
					DisplayString,
				b24LowerNonCritical
					DisplayString,
				b24LowerCritical
					DisplayString,
				b24LowerNonRecoverable
					DisplayString,
				b24SensorHealth
					INTEGER,
				b24SensorHealthEvents
					DisplayString,
				b24NegativeHysteresis
					DisplayString,
				b24PositiveHysteresis
					DisplayString,
				b24SensorType
					DisplayString,
				b24SensorFRUInfo
					DisplayString
			 }

 		b24Target OBJECT-TYPE
			SYNTAX DisplayString
			MAX-ACCESS not-accessible
			STATUS current
			DESCRIPTION
				"sensor Name"
			::= { blade24SensorTargetEntry 1 }
		
 		b24Current OBJECT-TYPE
			SYNTAX DisplayString
			MAX-ACCESS read-only
			STATUS current
			DESCRIPTION
				"Display the current value of a sensor."
			::= { blade24SensorTargetEntry 2 }
		
 		b24ThresholdsAll OBJECT-TYPE
			SYNTAX DisplayString
			MAX-ACCESS read-only
			STATUS current
			DESCRIPTION
				"All thresholds of a sensor"
			::= { blade24SensorTargetEntry 3 }
		
 		b24UpperCritical OBJECT-TYPE
			SYNTAX DisplayString
			MAX-ACCESS read-write
			STATUS current
			DESCRIPTION
				"Upper critical thresholds"
			::= { blade24SensorTargetEntry 4 }
		
 		b24UpperNonCritical OBJECT-TYPE
			SYNTAX DisplayString
			MAX-ACCESS read-write
			STATUS current
			DESCRIPTION
				"Upper non-critical thresholds"
			::= { blade24SensorTargetEntry 5 }
		
 		b24UpperNonRecoverable OBJECT-TYPE
			SYNTAX DisplayString
			MAX-ACCESS read-write
			STATUS current
			DESCRIPTION
				"Upper non-recoverable thresholds"
			::= { blade24SensorTargetEntry 6 }
		
 		b24LowerNonCritical OBJECT-TYPE
			SYNTAX DisplayString
			MAX-ACCESS read-write
			STATUS current
			DESCRIPTION
				"Lower non-critical thresholds"
			::= { blade24SensorTargetEntry 7 }
		
 		b24LowerCritical OBJECT-TYPE
			SYNTAX DisplayString
			MAX-ACCESS read-write
			STATUS current
			DESCRIPTION
				"Lower critical thresholds"
			::= { blade24SensorTargetEntry 8 }
		
 		b24LowerNonRecoverable OBJECT-TYPE
			SYNTAX DisplayString
			MAX-ACCESS read-write
			STATUS current
			DESCRIPTION
				"Lower non-recoverable thresholds"
			::= { blade24SensorTargetEntry 9 }
		
 		b24SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade24SensorTargetEntry 10 }
		
 		b24SensorHealthEvents OBJECT-TYPE
			SYNTAX DisplayString
			MAX-ACCESS read-only
			STATUS current
			DESCRIPTION
				"Events that contribute to the b14Health of the b14Location.  
				This is a list of events currently happening on the 
				b14Location."
			::= { blade24SensorTargetEntry 11 }
		
		
 		b24NegativeHysteresis OBJECT-TYPE
			SYNTAX DisplayString
			MAX-ACCESS read-write
			STATUS current
			DESCRIPTION
				"Get/Set the negativeHysteresis value"
			::= { blade24SensorTargetEntry 16 }
		
 		b24PositiveHysteresis OBJECT-TYPE
			SYNTAX DisplayString
			MAX-ACCESS read-write
			STATUS current
			DESCRIPTION
				"Get/Set the positiveHysteresis value."
			::= { blade24SensorTargetEntry 17 }
		
 		b24SensorType OBJECT-TYPE
			SYNTAX DisplayString
			MAX-ACCESS read-only
			STATUS current
			DESCRIPTION
				"Get the type of the sensor."
			::= { blade24SensorTargetEntry 18 }
		
 		b24SensorFRUInfo OBJECT-TYPE
			SYNTAX DisplayString
			MAX-ACCESS read-only
			STATUS current
			DESCRIPTION
				"Get the fruinfo of the sensor."
			::= { blade24SensorTargetEntry 19 }
		
 		blade24FruTable OBJECT-TYPE
			SYNTAX SEQUENCE OF Blade24FruEntry
			MAX-ACCESS not-accessible
			STATUS current
			DESCRIPTION
				"A table containing the list of FRU information."
			::= { blade24 2002 }
		
 		blade24FruEntry OBJECT-TYPE
			SYNTAX Blade24FruEntry
			MAX-ACCESS not-accessible
			STATUS current
			DESCRIPTION
				"Information about a particular current FRU."
			INDEX { b14fruNumber }
			::= { blade24FruTable 1 }
		
		Blade24FruEntry ::=
			SEQUENCE { 
				b24fruNumber
					INTEGER,
				b24FruHotSwapState
					DisplayString,
				b24FruLedProperties
					DisplayString,
				b24FRUControl
					INTEGER,
				b24FRULabel
					DisplayString,
				b24ResetReason
					DisplayString
			 }

 		b24fruNumber OBJECT-TYPE
			SYNTAX INTEGER
			MAX-ACCESS not-accessible
			STATUS current
			DESCRIPTION
				" "
			::= { blade24FruEntry 1 }
		
 		b24FruHotSwapState OBJECT-TYPE
			SYNTAX DisplayString
			MAX-ACCESS read-only
			STATUS current
			DESCRIPTION
				"Retrieve the hot swap state of the FRU from the 
				internally known hot swap states of blade14."
			::= { blade24FruEntry 3 }
		
 		b24FruLedProperties OBJECT-TYPE
			SYNTAX DisplayString
			MAX-ACCESS read-only
			STATUS current
			DESCRIPTION
				"Retrieves the LED support information from a FRU. Returns a comma separated
				list of LEDS and the number of FRU supported user LEDs."
			::= { blade24FruEntry 4 }

		

		b24FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade24FruEntry 9 }
		
 		b24FRULabel OBJECT-TYPE
			SYNTAX DisplayString
			MAX-ACCESS read-only
			STATUS current
			DESCRIPTION
				"Get fru label of blade14."
			::= { blade24FruEntry 10 }
		
 		b24ResetReason OBJECT-TYPE
			SYNTAX DisplayString
			MAX-ACCESS read-only
			STATUS current
			DESCRIPTION
				"Delete fru label of smm."
			::= { blade24FruEntry 11 }
		
 		blade24FruLedTable OBJECT-TYPE
			SYNTAX SEQUENCE OF Blade24FruLedEntry
			MAX-ACCESS not-accessible
			STATUS current
			DESCRIPTION
				"A table containing the list of led information."
			::= { blade24 2003 }
		
 		blade24FruLedEntry OBJECT-TYPE
			SYNTAX Blade24FruLedEntry
			MAX-ACCESS not-accessible
			STATUS current
			DESCRIPTION
				"Information about a particular current led."
			INDEX { b14FruID, b14FruLed }
			::= { blade24FruLedTable 1 }
		
		Blade24FruLedEntry ::=
			SEQUENCE { 
				b24FruID
					INTEGER,
				b24FruLed
					DisplayString,
				b24FruLedColorProps
					DisplayString,
				b24FruLedState
					DisplayString
			 }

 		b24FruID OBJECT-TYPE
			SYNTAX INTEGER
			MAX-ACCESS not-accessible
			STATUS current
			DESCRIPTION
				" "
			::= { blade24FruLedEntry 1 }
		
 		b24FruLed OBJECT-TYPE
			SYNTAX DisplayString
			MAX-ACCESS not-accessible
			STATUS current
			DESCRIPTION
				" "
			::= { blade24FruLedEntry 2 }
		
 		b24FruLedColorProps OBJECT-TYPE
			SYNTAX DisplayString
			MAX-ACCESS read-only
			STATUS current
			DESCRIPTION
				"Finds out what colors are supported by the LED"
			::= { blade24FruLedEntry 3 }
		
 		b24FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade24FruLedEntry 4 }
		
 		blade24FruDescriptionTable OBJECT-TYPE
			SYNTAX SEQUENCE OF Blade24FruDescriptionEntry
			MAX-ACCESS not-accessible
			STATUS current
			DESCRIPTION
				"A table containing the list of blade14 FRU information."
			::= { blade24 2004 }
		
 		blade24FruDescriptionEntry OBJECT-TYPE
			SYNTAX Blade24FruDescriptionEntry
			MAX-ACCESS not-accessible
			STATUS current
			DESCRIPTION
				"Information about a particular current FRU."
			INDEX { b14fruNum }
			::= { blade24FruDescriptionTable 1 }
		
		Blade24FruDescriptionEntry ::=
			SEQUENCE { 
				b24fruNum
					INTEGER,
				b24fruBoardDescription
					DisplayString,
				b24fruBoardManufacturer
					DisplayString,
				b24fruBoardPartNumber
					DisplayString,
				b24fruBoardSerialNumber
					DisplayString,
				b24fruBoardManufactureDate
					DisplayString,
				b24fruProductDescription
					DisplayString,
				b24fruProductManufacturer
					DisplayString,
				b24fruProductPartNumber
					DisplayString,
				b24fruProductSerialNumber
					DisplayString,
				b24fruProductRevision
					DisplayString,
				b24fruAll
					DisplayString
			 }

 		b24fruNum OBJECT-TYPE
			SYNTAX INTEGER
			MAX-ACCESS not-accessible
			STATUS current
			DESCRIPTION
				"blade14 FRU's INDEX"
			::= { blade24FruDescriptionEntry 1 }
		
 		b24fruBoardDescription OBJECT-TYPE
			SYNTAX DisplayString
			MAX-ACCESS read-only
			STATUS current
			DESCRIPTION
				"Used to read the Board Description from the blade14 fru."
			::= { blade24FruDescriptionEntry 2 }
		
 		b24fruBoardManufacturer OBJECT-TYPE
			SYNTAX DisplayString
			MAX-ACCESS read-only
			STATUS current
			DESCRIPTION
				"Used to read the Board Manufacturer from the bladef14 fru."
			::= { blade24FruDescriptionEntry 3 }
		
 		b24fruBoardPartNumber OBJECT-TYPE
			SYNTAX DisplayString
			MAX-ACCESS read-only
			STATUS current
			DESCRIPTION
				"Used to read the Board Part Number from the blade14 fru."
			::= { blade24FruDescriptionEntry 4 }
		
 		b24fruBoardSerialNumber OBJECT-TYPE
			SYNTAX DisplayString
			MAX-ACCESS read-only
			STATUS current
			DESCRIPTION
				"Used to read the Board Serial Number from the blade14 fru."
			::= { blade24FruDescriptionEntry 5 }
		
 		b24fruBoardManufactureDate OBJECT-TYPE
			SYNTAX DisplayString
			MAX-ACCESS read-only
			STATUS current
			DESCRIPTION
				"Used to read the Board Manufacture Date from the blade14 fru."
			::= { blade24FruDescriptionEntry 6 }
		
 		b24fruProductDescription OBJECT-TYPE
			SYNTAX DisplayString
			MAX-ACCESS read-only
			STATUS current
			DESCRIPTION
				"Used to read the Product Description from the blade14 fru."
			::= { blade24FruDescriptionEntry 7 }
		
 		b24fruProductManufacturer OBJECT-TYPE
			SYNTAX DisplayString
			MAX-ACCESS read-only
			STATUS current
			DESCRIPTION
				"Used to read the Product Manufacturer from the blade14 fru."
			::= { blade24FruDescriptionEntry 8 }
		
 		b24fruProductPartNumber OBJECT-TYPE
			SYNTAX DisplayString
			MAX-ACCESS read-only
			STATUS current
			DESCRIPTION
				"Used to read the Product Part Number from the blade14 fru."
			::= { blade24FruDescriptionEntry 9 }
		
 		b24fruProductSerialNumber OBJECT-TYPE
			SYNTAX DisplayString
			MAX-ACCESS read-only
			STATUS current
			DESCRIPTION
				"Used to read the Product Serial Number from the blade14 fru."
			::= { blade24FruDescriptionEntry 10 }
		
 		b24fruProductRevision OBJECT-TYPE
			SYNTAX DisplayString
			MAX-ACCESS read-only
			STATUS current
			DESCRIPTION
				"Used to read the Product Revision from the blade14 fru."
			::= { blade24FruDescriptionEntry 13 }
		
 		b24fruAll OBJECT-TYPE
			SYNTAX DisplayString
			MAX-ACCESS read-only
			STATUS current
			DESCRIPTION
				"Used to read the fru info all."
			::= { blade24FruDescriptionEntry 14 }
		
		blade24CPUTable OBJECT-TYPE
			SYNTAX SEQUENCE OF Blade24CPUEntry
			MAX-ACCESS not-accessible
			STATUS current
			DESCRIPTION
				"A table containing the list of Blade1 FRU information."
			::= { blade24 2006 }
		
		blade24CPUEntry OBJECT-TYPE
			SYNTAX Blade24CPUEntry
			MAX-ACCESS not-accessible
			STATUS current
			DESCRIPTION
				"Information about a particular current FRU."
			INDEX { b24CPUIndex }
			::= { blade24CPUTable 1 }
		
		Blade24CPUEntry ::=
			SEQUENCE { 
				b24CPUIndex
					INTEGER,
				b24CPUMark
					DisplayString,
				b24CPUInfo
					DisplayString,
				b24CPUPresent
					INTEGER,
				b24CPUHealth
					INTEGER,
				b24CPULocation
					DisplayString
			 }

		b24CPUIndex OBJECT-TYPE
			SYNTAX INTEGER
			MAX-ACCESS not-accessible
			STATUS current
			DESCRIPTION
				"CPU INDEX"
			::= { blade24CPUEntry 1 }
		
		b24CPUMark OBJECT-TYPE
			SYNTAX DisplayString
			MAX-ACCESS read-only
			STATUS current
			DESCRIPTION
				"Get the CPU silk-screen."
			::= { blade24CPUEntry 2 }
		
		b24CPUInfo OBJECT-TYPE
			SYNTAX DisplayString
			MAX-ACCESS read-only
			STATUS current
			DESCRIPTION
				"Get the CPU description of vendor, type and frequency."
			::= { blade24CPUEntry 3 }
		
		b24CPUPresent OBJECT-TYPE
			SYNTAX INTEGER
			MAX-ACCESS read-only
			STATUS current
			DESCRIPTION
				"Get the CPU presence status."
			::= { blade24CPUEntry 4 }
		
		b24CPUHealth OBJECT-TYPE
			SYNTAX INTEGER
			MAX-ACCESS read-only
			STATUS current
			DESCRIPTION
				"Get the CPU health status."
			::= { blade24CPUEntry 5 }
		
		b24CPULocation OBJECT-TYPE
			SYNTAX DisplayString
			MAX-ACCESS read-only
			STATUS current
			DESCRIPTION
				"Get the CPU location."
			::= { blade24CPUEntry 6 }
		
		blade24MemoryTable OBJECT-TYPE
			SYNTAX SEQUENCE OF Blade24MemoryEntry
			MAX-ACCESS not-accessible
			STATUS current
			DESCRIPTION
				"A table containing the list of Blade1 FRU information."
			::= { blade24 2007 }
		
		blade24MemoryEntry OBJECT-TYPE
			SYNTAX Blade24MemoryEntry
			MAX-ACCESS not-accessible
			STATUS current
			DESCRIPTION
				"Information about a particular current FRU."
			INDEX { b24MEMIndex }
			::= { blade24MemoryTable 1 }
		
		Blade24MemoryEntry ::=
			SEQUENCE { 
				b24MEMIndex
					INTEGER,
				b24MEMMark
					DisplayString,
				b24MEMInfo
					DisplayString,
				b24MEMPresent
					INTEGER,
				b24MEMHealth
					INTEGER,
				b24MEMLocation
					DisplayString
			 }

		b24MEMIndex OBJECT-TYPE
			SYNTAX INTEGER
			MAX-ACCESS not-accessible
			STATUS current
			DESCRIPTION
				"MEMORY INDEX"
			::= { blade24MemoryEntry 1 }
		
		b24MEMMark OBJECT-TYPE
			SYNTAX DisplayString
			MAX-ACCESS read-only
			STATUS current
			DESCRIPTION
				"Get the memory silk-screen."
			::= { blade24MemoryEntry 2 }
		
		b24MEMInfo OBJECT-TYPE
			SYNTAX DisplayString
			MAX-ACCESS read-only
			STATUS current
			DESCRIPTION
				"Get the memory description of vendor, frequency and capacity."
			::= { blade24MemoryEntry 3 }
		
		b24MEMPresent OBJECT-TYPE
			SYNTAX INTEGER
			MAX-ACCESS read-only
			STATUS current
			DESCRIPTION
				"Get the memory presence status."
			::= { blade24MemoryEntry 4 }
		
		b24MEMHealth OBJECT-TYPE
			SYNTAX INTEGER
			MAX-ACCESS read-only
			STATUS current
			DESCRIPTION
				"Get the memory health status."
			::= { blade24MemoryEntry 5 }
		
		b24MEMLocation OBJECT-TYPE
			SYNTAX DisplayString
			MAX-ACCESS read-only
			STATUS current
			DESCRIPTION
				"Get the memory location."
			::= { blade24MemoryEntry 6 }
		
		blade24MezzTable OBJECT-TYPE
			SYNTAX SEQUENCE OF Blade24MezzEntry
			MAX-ACCESS not-accessible
			STATUS current
			DESCRIPTION
				"A table containing the list of Blade1 FRU information."
			::= { blade24 2008 }
		
		blade24MezzEntry OBJECT-TYPE
			SYNTAX Blade24MezzEntry
			MAX-ACCESS not-accessible
			STATUS current
			DESCRIPTION
				"Information about a particular current FRU."
			INDEX { b24MezzIndex }
			::= { blade24MezzTable 1 }
		
		Blade24MezzEntry ::=
			SEQUENCE { 
				b24MezzIndex
					INTEGER,
				b24MezzMark
					DisplayString,
				b24MezzInfo
					DisplayString,
				b24MezzPresent
					INTEGER,
				b24MezzHealth
					INTEGER,
				b24MezzLocation
					DisplayString,
				b24MezzMac
					DisplayString
			 }

		b24MezzIndex OBJECT-TYPE
			SYNTAX INTEGER
			MAX-ACCESS not-accessible
			STATUS current
			DESCRIPTION
				"MEZZ INDEX"
			::= { blade24MezzEntry 1 }
		
		b24MezzMark OBJECT-TYPE
			SYNTAX DisplayString
			MAX-ACCESS read-only
			STATUS current
			DESCRIPTION
				"Get the MEZZ silk-screen."
			::= { blade24MezzEntry 2 }
		
		b24MezzInfo OBJECT-TYPE
			SYNTAX DisplayString
			MAX-ACCESS read-only
			STATUS current
			DESCRIPTION
				"Get the MEZZ description of type."
			::= { blade24MezzEntry 3 }
		
		b24MezzPresent OBJECT-TYPE
			SYNTAX INTEGER
			MAX-ACCESS read-only
			STATUS current
			DESCRIPTION
				"Get the MEZZ presence status."
			::= { blade24MezzEntry 4 }
		
		b24MezzHealth OBJECT-TYPE
			SYNTAX INTEGER
			MAX-ACCESS read-only
			STATUS current
			DESCRIPTION
				"Get the MEZZ health status."
			::= { blade24MezzEntry 5 }
		
		b24MezzLocation OBJECT-TYPE
			SYNTAX DisplayString
			MAX-ACCESS read-only
			STATUS current
			DESCRIPTION
				"Get the MEZZ location."
			::= { blade24MezzEntry 6 }
		
		b24MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade24MezzEntry 7 }
		
		blade24DiskTable OBJECT-TYPE
			SYNTAX SEQUENCE OF Blade24DiskEntry
			MAX-ACCESS not-accessible
			STATUS current
			DESCRIPTION
				"A table containing the list of Blade1 FRU information."
			::= { blade24 2009 }
		
		blade24DiskEntry OBJECT-TYPE
			SYNTAX Blade24DiskEntry
			MAX-ACCESS not-accessible
			STATUS current
			DESCRIPTION
				"Information about a particular current FRU."
			INDEX { b24DiskIndex }
			::= { blade24DiskTable 1 }
		
		Blade24DiskEntry ::=
			SEQUENCE { 
				b24DiskIndex
					INTEGER,
				b24DiskMark
					DisplayString,
				b24DiskInfo
					DisplayString,
				b24DiskPresent
					INTEGER,
				b24DiskHealth
					INTEGER,
				b24DiskLocation
					DisplayString
			 }

		b24DiskIndex OBJECT-TYPE
			SYNTAX INTEGER
			MAX-ACCESS not-accessible
			STATUS current
			DESCRIPTION
				"DISK INDEX"
			::= { blade24DiskEntry 1 }
		
		b24DiskMark OBJECT-TYPE
			SYNTAX DisplayString
			MAX-ACCESS read-only
			STATUS current
			DESCRIPTION
				"Get the disk silk-screen."
			::= { blade24DiskEntry 2 }
		
		b24DiskInfo OBJECT-TYPE
			SYNTAX DisplayString
			MAX-ACCESS read-only
			STATUS current
			DESCRIPTION
				"Get the disk description of vendor, capacity and speed."
			::= { blade24DiskEntry 3 }
		
		b24DiskPresent OBJECT-TYPE
			SYNTAX INTEGER
			MAX-ACCESS read-only
			STATUS current
			DESCRIPTION
				"Get the disk presence status."
			::= { blade24DiskEntry 4 }
		
		b24DiskHealth OBJECT-TYPE
			SYNTAX INTEGER
			MAX-ACCESS read-only
			STATUS current
			DESCRIPTION
				"Get the disk health status."
			::= { blade24DiskEntry 5 }
		
		b24DiskLocation OBJECT-TYPE
			SYNTAX DisplayString
			MAX-ACCESS read-only
			STATUS current
			DESCRIPTION
				"Get the disk location."
			::= { blade24DiskEntry 6 }
		
		blade24SecretKvmVmmTable OBJECT-TYPE
			SYNTAX SEQUENCE OF Blade24SecretKvmVmmEntry
			MAX-ACCESS not-accessible
			STATUS current
			DESCRIPTION
				"A table containing the list of Blade24 KVM&VMM secret information."
			::= { blade24 2010 }

		blade24SecretKvmVmmEntry OBJECT-TYPE
			SYNTAX Blade24SecretKvmVmmEntry
			MAX-ACCESS not-accessible
			STATUS current
			DESCRIPTION
				"Information about a particular current KVM&VMM."
			INDEX { b24SecretKvmVmmIndex }
			::= { blade24SecretKvmVmmTable 1 }
		Blade24SecretKvmVmmEntry ::=
			SEQUENCE { 
				b24SecretKvmVmmIndex
					INTEGER,
				b24SecretKvmState
					INTEGER,
				b24SecretVmmState
					INTEGER,
				b24MMSecretVmmKey
					DisplayString,
				b24SecretVmmKey
					DisplayString
			 }
		b24SecretKvmVmmIndex OBJECT-TYPE
			SYNTAX INTEGER
			MAX-ACCESS not-accessible
			STATUS current
			DESCRIPTION
				"KVM&VMM INDEX."
			::= { blade24SecretKvmVmmEntry 1 }
		b24SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade24SecretKvmVmmEntry 2 }
		b24SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade24SecretKvmVmmEntry 3 }
		b24MMSecretVmmKey OBJECT-TYPE
			SYNTAX DisplayString
			MAX-ACCESS read-only
			STATUS current
			DESCRIPTION
				"Get the MM secret VMM key."
			::= { blade24SecretKvmVmmEntry 4 }
		b24SecretVmmKey OBJECT-TYPE
			SYNTAX DisplayString
			MAX-ACCESS read-write
			STATUS current
			DESCRIPTION
				"Set the secret VMM key."
			::= { blade24SecretKvmVmmEntry 5 }
		blade25 OBJECT IDENTIFIER ::= { blades 25 }

		
 		b25DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade25 4 }
		
 		b25PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade25 5 }
		
 		b25Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade25 6 }

		
 		b25Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade25 8 }
		
 		b25HealthEvents OBJECT-TYPE
			SYNTAX DisplayString
			MAX-ACCESS read-only
			STATUS current
			DESCRIPTION
				"Events that contribute to the b14Health of the b14Location.  
				This is a list of events currently happening on the 
				b14Location."
			::= { blade25 9 }
		
 		b25ClearSEL OBJECT-TYPE
			SYNTAX INTEGER { clear(1) }
			MAX-ACCESS read-write
			STATUS current
			DESCRIPTION
				"Clean the BMC's SEL on the board."
			::= { blade25 12 }
		
 		b25ExDiskBoardPresence OBJECT-TYPE
			SYNTAX INTEGER
				{
				not-present(0),
				present(1)
				}
			MAX-ACCESS read-only
			STATUS current
			DESCRIPTION
				"Used to find out if the extended disk board is present.
				0 - not present
				1 - present"
			::= { blade25 14 }
		
 		b25BladeVersion OBJECT-TYPE
			SYNTAX DisplayString
			MAX-ACCESS read-only
			STATUS current
			DESCRIPTION
				"display the Version of board14."
			::= { blade25 20 }
		
 		b25MACAddress OBJECT-TYPE
			SYNTAX DisplayString
			MAX-ACCESS read-only
			STATUS current
			DESCRIPTION
				"display the MACAddress of board14."
			::= { blade25 21 }
		
				
							
		
 		b25Safepwofftime OBJECT-TYPE
			SYNTAX INTEGER
			MAX-ACCESS read-write
			STATUS current
			DESCRIPTION
				"the safe poweroff time.
				"
			::= { blade25 26 }
		
 		b25BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]   
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade25 32 }
		
 		b25Systeminfo OBJECT-TYPE
			SYNTAX DisplayString
			MAX-ACCESS read-write
			STATUS current
			DESCRIPTION
				"display the system information of board14."
			::= { blade25 36 }

		
 		b25SystemProperties OBJECT-TYPE
			SYNTAX DisplayString
			MAX-ACCESS read-only
			STATUS current
			DESCRIPTION
				"Get the power of blade1."
			::= { blade25 39 }
		
 		b25BiosCfg OBJECT-TYPE
			SYNTAX DisplayString
			MAX-ACCESS read-write
			STATUS current
			DESCRIPTION
				"Get the power of blade1."
			::= { blade25 40 }
		
 		b25WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade25 41 }
		
 		b25RealTimePower OBJECT-TYPE
			SYNTAX INTEGER
			MAX-ACCESS read-only
			STATUS current
			DESCRIPTION
				" "
			::= { blade25 43 }
		
 		b25PowerCapping OBJECT-TYPE
			SYNTAX DisplayString
			MAX-ACCESS read-write
			STATUS current
			DESCRIPTION
				" "
			::= { blade25 44 }
		
 		b25Powerreference OBJECT-TYPE
			SYNTAX INTEGER
			MAX-ACCESS read-only
			STATUS current
			DESCRIPTION
				" "
			::= { blade25 45 }
		
 		b25ClearBiosConfig OBJECT-TYPE
			SYNTAX INTEGER
			MAX-ACCESS read-write
			STATUS current
			DESCRIPTION
				" "
			::= { blade25 46 }
		
 		b25BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade25 47 }
		
 		b25BmcUserAdd OBJECT-TYPE
			SYNTAX DisplayString
			MAX-ACCESS read-write
			STATUS current
			DESCRIPTION
				"Used to Add the BMC User
				settable format:
				username,passwd"
			::= { blade25 48 }
		
 		b25BmcUserDel OBJECT-TYPE
			SYNTAX DisplayString
			MAX-ACCESS read-write
			STATUS current
			DESCRIPTION
				"Used to Del the BMC User
				settable format:
				username"
			::= { blade25 49 }
		
 		b25BmcUserPasswd OBJECT-TYPE
			SYNTAX DisplayString
			MAX-ACCESS read-write
			STATUS current
			DESCRIPTION
				"Used to Change the BMC User Passwd
				settable format:
				username,passwd"
			::= { blade25 50 }
		
 		b25BmcUserpropertychg OBJECT-TYPE
			SYNTAX DisplayString
			MAX-ACCESS read-write
			STATUS current
			DESCRIPTION
				"Used to Change the BMC User Property
				settable format:
				username,property"
			::= { blade25 51 }
		
 		b25BmcGateway OBJECT-TYPE
			SYNTAX DisplayString
			MAX-ACCESS read-write
			STATUS current
			DESCRIPTION
				"Read or set the gateway."
			::= { blade25 52 }
		
 		b25SlotBitmap OBJECT-TYPE
			SYNTAX INTEGER
			MAX-ACCESS read-only
			STATUS current
			DESCRIPTION
				" "
			::= { blade25 55 }
		
		b25systemGuid OBJECT-TYPE
			SYNTAX DisplayString
			MAX-ACCESS read-only
			STATUS current
			DESCRIPTION
				" "
			::= { blade25 56 }
		
		b25ProductName OBJECT-TYPE
			SYNTAX DisplayString
			MAX-ACCESS read-only
			STATUS current
			DESCRIPTION
				"display the Version of board14."
			::= { blade25 57 }
		
		b25BundleVersion OBJECT-TYPE
			SYNTAX DisplayString
			MAX-ACCESS read-write
			STATUS current
			DESCRIPTION
				"Get or set the board25 bundle version."
			::= { blade25 58 }

 		blade25SensorTargetTable OBJECT-TYPE
			SYNTAX SEQUENCE OF Blade25SensorTargetEntry
			MAX-ACCESS not-accessible
			STATUS current
			DESCRIPTION
				"A table containing the list of sensor information."
			::= { blade25 2001 }
		
 		blade25SensorTargetEntry OBJECT-TYPE
			SYNTAX Blade25SensorTargetEntry
			MAX-ACCESS not-accessible
			STATUS current
			DESCRIPTION
				"Information about a particular current sensor."
			INDEX { b14Target }
			::= { blade25SensorTargetTable 1 }
		
		Blade25SensorTargetEntry ::=
			SEQUENCE { 
				b25Target
					DisplayString,
				b25Current
					DisplayString,
				b25ThresholdsAll
					DisplayString,
				b25UpperCritical
					DisplayString,
				b25UpperNonCritical
					DisplayString,
				b25UpperNonRecoverable
					DisplayString,
				b25LowerNonCritical
					DisplayString,
				b25LowerCritical
					DisplayString,
				b25LowerNonRecoverable
					DisplayString,
				b25SensorHealth
					INTEGER,
				b25SensorHealthEvents
					DisplayString,
				b25NegativeHysteresis
					DisplayString,
				b25PositiveHysteresis
					DisplayString,
				b25SensorType
					DisplayString,
				b25SensorFRUInfo
					DisplayString
			 }

 		b25Target OBJECT-TYPE
			SYNTAX DisplayString
			MAX-ACCESS not-accessible
			STATUS current
			DESCRIPTION
				"sensor Name"
			::= { blade25SensorTargetEntry 1 }
		
 		b25Current OBJECT-TYPE
			SYNTAX DisplayString
			MAX-ACCESS read-only
			STATUS current
			DESCRIPTION
				"Display the current value of a sensor."
			::= { blade25SensorTargetEntry 2 }
		
 		b25ThresholdsAll OBJECT-TYPE
			SYNTAX DisplayString
			MAX-ACCESS read-only
			STATUS current
			DESCRIPTION
				"All thresholds of a sensor"
			::= { blade25SensorTargetEntry 3 }
		
 		b25UpperCritical OBJECT-TYPE
			SYNTAX DisplayString
			MAX-ACCESS read-write
			STATUS current
			DESCRIPTION
				"Upper critical thresholds"
			::= { blade25SensorTargetEntry 4 }
		
 		b25UpperNonCritical OBJECT-TYPE
			SYNTAX DisplayString
			MAX-ACCESS read-write
			STATUS current
			DESCRIPTION
				"Upper non-critical thresholds"
			::= { blade25SensorTargetEntry 5 }
		
 		b25UpperNonRecoverable OBJECT-TYPE
			SYNTAX DisplayString
			MAX-ACCESS read-write
			STATUS current
			DESCRIPTION
				"Upper non-recoverable thresholds"
			::= { blade25SensorTargetEntry 6 }
		
 		b25LowerNonCritical OBJECT-TYPE
			SYNTAX DisplayString
			MAX-ACCESS read-write
			STATUS current
			DESCRIPTION
				"Lower non-critical thresholds"
			::= { blade25SensorTargetEntry 7 }
		
 		b25LowerCritical OBJECT-TYPE
			SYNTAX DisplayString
			MAX-ACCESS read-write
			STATUS current
			DESCRIPTION
				"Lower critical thresholds"
			::= { blade25SensorTargetEntry 8 }
		
 		b25LowerNonRecoverable OBJECT-TYPE
			SYNTAX DisplayString
			MAX-ACCESS read-write
			STATUS current
			DESCRIPTION
				"Lower non-recoverable thresholds"
			::= { blade25SensorTargetEntry 9 }
		
 		b25SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade25SensorTargetEntry 10 }
		
 		b25SensorHealthEvents OBJECT-TYPE
			SYNTAX DisplayString
			MAX-ACCESS read-only
			STATUS current
			DESCRIPTION
				"Events that contribute to the b14Health of the b14Location.  
				This is a list of events currently happening on the 
				b14Location."
			::= { blade25SensorTargetEntry 11 }
		
		
 		b25NegativeHysteresis OBJECT-TYPE
			SYNTAX DisplayString
			MAX-ACCESS read-write
			STATUS current
			DESCRIPTION
				"Get/Set the negativeHysteresis value"
			::= { blade25SensorTargetEntry 16 }
		
 		b25PositiveHysteresis OBJECT-TYPE
			SYNTAX DisplayString
			MAX-ACCESS read-write
			STATUS current
			DESCRIPTION
				"Get/Set the positiveHysteresis value."
			::= { blade25SensorTargetEntry 17 }
		
 		b25SensorType OBJECT-TYPE
			SYNTAX DisplayString
			MAX-ACCESS read-only
			STATUS current
			DESCRIPTION
				"Get the type of the sensor."
			::= { blade25SensorTargetEntry 18 }
		
 		b25SensorFRUInfo OBJECT-TYPE
			SYNTAX DisplayString
			MAX-ACCESS read-only
			STATUS current
			DESCRIPTION
				"Get the fruinfo of the sensor."
			::= { blade25SensorTargetEntry 19 }
		
 		blade25FruTable OBJECT-TYPE
			SYNTAX SEQUENCE OF Blade25FruEntry
			MAX-ACCESS not-accessible
			STATUS current
			DESCRIPTION
				"A table containing the list of FRU information."
			::= { blade25 2002 }
		
 		blade25FruEntry OBJECT-TYPE
			SYNTAX Blade25FruEntry
			MAX-ACCESS not-accessible
			STATUS current
			DESCRIPTION
				"Information about a particular current FRU."
			INDEX { b14fruNumber }
			::= { blade25FruTable 1 }
		
		Blade25FruEntry ::=
			SEQUENCE { 
				b25fruNumber
					INTEGER,
				b25FruHotSwapState
					DisplayString,
				b25FruLedProperties
					DisplayString,
				b25FRUControl
					INTEGER,
				b25FRULabel
					DisplayString,
				b25ResetReason
					DisplayString
			 }

 		b25fruNumber OBJECT-TYPE
			SYNTAX INTEGER
			MAX-ACCESS not-accessible
			STATUS current
			DESCRIPTION
				" "
			::= { blade25FruEntry 1 }
		
 		b25FruHotSwapState OBJECT-TYPE
			SYNTAX DisplayString
			MAX-ACCESS read-only
			STATUS current
			DESCRIPTION
				"Retrieve the hot swap state of the FRU from the 
				internally known hot swap states of blade14."
			::= { blade25FruEntry 3 }
		
 		b25FruLedProperties OBJECT-TYPE
			SYNTAX DisplayString
			MAX-ACCESS read-only
			STATUS current
			DESCRIPTION
				"Retrieves the LED support information from a FRU. Returns a comma separated
				list of LEDS and the number of FRU supported user LEDs."
			::= { blade25FruEntry 4 }

		

		b25FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade25FruEntry 9 }
		
 		b25FRULabel OBJECT-TYPE
			SYNTAX DisplayString
			MAX-ACCESS read-only
			STATUS current
			DESCRIPTION
				"Get fru label of blade14."
			::= { blade25FruEntry 10 }
		
 		b25ResetReason OBJECT-TYPE
			SYNTAX DisplayString
			MAX-ACCESS read-only
			STATUS current
			DESCRIPTION
				"Delete fru label of smm."
			::= { blade25FruEntry 11 }
		
 		blade25FruLedTable OBJECT-TYPE
			SYNTAX SEQUENCE OF Blade25FruLedEntry
			MAX-ACCESS not-accessible
			STATUS current
			DESCRIPTION
				"A table containing the list of led information."
			::= { blade25 2003 }
		
 		blade25FruLedEntry OBJECT-TYPE
			SYNTAX Blade25FruLedEntry
			MAX-ACCESS not-accessible
			STATUS current
			DESCRIPTION
				"Information about a particular current led."
			INDEX { b14FruID, b14FruLed }
			::= { blade25FruLedTable 1 }
		
		Blade25FruLedEntry ::=
			SEQUENCE { 
				b25FruID
					INTEGER,
				b25FruLed
					DisplayString,
				b25FruLedColorProps
					DisplayString,
				b25FruLedState
					DisplayString
			 }

 		b25FruID OBJECT-TYPE
			SYNTAX INTEGER
			MAX-ACCESS not-accessible
			STATUS current
			DESCRIPTION
				" "
			::= { blade25FruLedEntry 1 }
		
 		b25FruLed OBJECT-TYPE
			SYNTAX DisplayString
			MAX-ACCESS not-accessible
			STATUS current
			DESCRIPTION
				" "
			::= { blade25FruLedEntry 2 }
		
 		b25FruLedColorProps OBJECT-TYPE
			SYNTAX DisplayString
			MAX-ACCESS read-only
			STATUS current
			DESCRIPTION
				"Finds out what colors are supported by the LED"
			::= { blade25FruLedEntry 3 }
		
 		b25FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade25FruLedEntry 4 }
		
 		blade25FruDescriptionTable OBJECT-TYPE
			SYNTAX SEQUENCE OF Blade25FruDescriptionEntry
			MAX-ACCESS not-accessible
			STATUS current
			DESCRIPTION
				"A table containing the list of blade14 FRU information."
			::= { blade25 2004 }
		
 		blade25FruDescriptionEntry OBJECT-TYPE
			SYNTAX Blade25FruDescriptionEntry
			MAX-ACCESS not-accessible
			STATUS current
			DESCRIPTION
				"Information about a particular current FRU."
			INDEX { b14fruNum }
			::= { blade25FruDescriptionTable 1 }
		
		Blade25FruDescriptionEntry ::=
			SEQUENCE { 
				b25fruNum
					INTEGER,
				b25fruBoardDescription
					DisplayString,
				b25fruBoardManufacturer
					DisplayString,
				b25fruBoardPartNumber
					DisplayString,
				b25fruBoardSerialNumber
					DisplayString,
				b25fruBoardManufactureDate
					DisplayString,
				b25fruProductDescription
					DisplayString,
				b25fruProductManufacturer
					DisplayString,
				b25fruProductPartNumber
					DisplayString,
				b25fruProductSerialNumber
					DisplayString,
				b25fruProductRevision
					DisplayString,
				b25fruAll
					DisplayString
			 }

 		b25fruNum OBJECT-TYPE
			SYNTAX INTEGER
			MAX-ACCESS not-accessible
			STATUS current
			DESCRIPTION
				"blade14 FRU's INDEX"
			::= { blade25FruDescriptionEntry 1 }
		
 		b25fruBoardDescription OBJECT-TYPE
			SYNTAX DisplayString
			MAX-ACCESS read-only
			STATUS current
			DESCRIPTION
				"Used to read the Board Description from the blade14 fru."
			::= { blade25FruDescriptionEntry 2 }
		
 		b25fruBoardManufacturer OBJECT-TYPE
			SYNTAX DisplayString
			MAX-ACCESS read-only
			STATUS current
			DESCRIPTION
				"Used to read the Board Manufacturer from the bladef14 fru."
			::= { blade25FruDescriptionEntry 3 }
		
 		b25fruBoardPartNumber OBJECT-TYPE
			SYNTAX DisplayString
			MAX-ACCESS read-only
			STATUS current
			DESCRIPTION
				"Used to read the Board Part Number from the blade14 fru."
			::= { blade25FruDescriptionEntry 4 }
		
 		b25fruBoardSerialNumber OBJECT-TYPE
			SYNTAX DisplayString
			MAX-ACCESS read-only
			STATUS current
			DESCRIPTION
				"Used to read the Board Serial Number from the blade14 fru."
			::= { blade25FruDescriptionEntry 5 }
		
 		b25fruBoardManufactureDate OBJECT-TYPE
			SYNTAX DisplayString
			MAX-ACCESS read-only
			STATUS current
			DESCRIPTION
				"Used to read the Board Manufacture Date from the blade14 fru."
			::= { blade25FruDescriptionEntry 6 }
		
 		b25fruProductDescription OBJECT-TYPE
			SYNTAX DisplayString
			MAX-ACCESS read-only
			STATUS current
			DESCRIPTION
				"Used to read the Product Description from the blade14 fru."
			::= { blade25FruDescriptionEntry 7 }
		
 		b25fruProductManufacturer OBJECT-TYPE
			SYNTAX DisplayString
			MAX-ACCESS read-only
			STATUS current
			DESCRIPTION
				"Used to read the Product Manufacturer from the blade14 fru."
			::= { blade25FruDescriptionEntry 8 }
		
 		b25fruProductPartNumber OBJECT-TYPE
			SYNTAX DisplayString
			MAX-ACCESS read-only
			STATUS current
			DESCRIPTION
				"Used to read the Product Part Number from the blade14 fru."
			::= { blade25FruDescriptionEntry 9 }
		
 		b25fruProductSerialNumber OBJECT-TYPE
			SYNTAX DisplayString
			MAX-ACCESS read-only
			STATUS current
			DESCRIPTION
				"Used to read the Product Serial Number from the blade14 fru."
			::= { blade25FruDescriptionEntry 10 }
		
 		b25fruProductRevision OBJECT-TYPE
			SYNTAX DisplayString
			MAX-ACCESS read-only
			STATUS current
			DESCRIPTION
				"Used to read the Product Revision from the blade14 fru."
			::= { blade25FruDescriptionEntry 13 }
		
 		b25fruAll OBJECT-TYPE
			SYNTAX DisplayString
			MAX-ACCESS read-only
			STATUS current
			DESCRIPTION
				"Used to read the fru info all."
			::= { blade25FruDescriptionEntry 14 }
		
		blade25CPUTable OBJECT-TYPE
			SYNTAX SEQUENCE OF Blade25CPUEntry
			MAX-ACCESS not-accessible
			STATUS current
			DESCRIPTION
				"A table containing the list of Blade1 FRU information."
			::= { blade25 2006 }
		
		blade25CPUEntry OBJECT-TYPE
			SYNTAX Blade25CPUEntry
			MAX-ACCESS not-accessible
			STATUS current
			DESCRIPTION
				"Information about a particular current FRU."
			INDEX { b25CPUIndex }
			::= { blade25CPUTable 1 }
		
		Blade25CPUEntry ::=
			SEQUENCE { 
				b25CPUIndex
					INTEGER,
				b25CPUMark
					DisplayString,
				b25CPUInfo
					DisplayString,
				b25CPUPresent
					INTEGER,
				b25CPUHealth
					INTEGER,
				b25CPULocation
					DisplayString
			 }

		b25CPUIndex OBJECT-TYPE
			SYNTAX INTEGER
			MAX-ACCESS not-accessible
			STATUS current
			DESCRIPTION
				"CPU INDEX"
			::= { blade25CPUEntry 1 }
		
		b25CPUMark OBJECT-TYPE
			SYNTAX DisplayString
			MAX-ACCESS read-only
			STATUS current
			DESCRIPTION
				"Get the CPU silk-screen."
			::= { blade25CPUEntry 2 }
		
		b25CPUInfo OBJECT-TYPE
			SYNTAX DisplayString
			MAX-ACCESS read-only
			STATUS current
			DESCRIPTION
				"Get the CPU description of vendor, type and frequency."
			::= { blade25CPUEntry 3 }
		
		b25CPUPresent OBJECT-TYPE
			SYNTAX INTEGER
			MAX-ACCESS read-only
			STATUS current
			DESCRIPTION
				"Get the CPU presence status."
			::= { blade25CPUEntry 4 }
		
		b25CPUHealth OBJECT-TYPE
			SYNTAX INTEGER
			MAX-ACCESS read-only
			STATUS current
			DESCRIPTION
				"Get the CPU health status."
			::= { blade25CPUEntry 5 }
		
		b25CPULocation OBJECT-TYPE
			SYNTAX DisplayString
			MAX-ACCESS read-only
			STATUS current
			DESCRIPTION
				"Get the CPU location."
			::= { blade25CPUEntry 6 }
		
		blade25MemoryTable OBJECT-TYPE
			SYNTAX SEQUENCE OF Blade25MemoryEntry
			MAX-ACCESS not-accessible
			STATUS current
			DESCRIPTION
				"A table containing the list of Blade1 FRU information."
			::= { blade25 2007 }
		
		blade25MemoryEntry OBJECT-TYPE
			SYNTAX Blade25MemoryEntry
			MAX-ACCESS not-accessible
			STATUS current
			DESCRIPTION
				"Information about a particular current FRU."
			INDEX { b25MEMIndex }
			::= { blade25MemoryTable 1 }
		
		Blade25MemoryEntry ::=
			SEQUENCE { 
				b25MEMIndex
					INTEGER,
				b25MEMMark
					DisplayString,
				b25MEMInfo
					DisplayString,
				b25MEMPresent
					INTEGER,
				b25MEMHealth
					INTEGER,
				b25MEMLocation
					DisplayString
			 }

		b25MEMIndex OBJECT-TYPE
			SYNTAX INTEGER
			MAX-ACCESS not-accessible
			STATUS current
			DESCRIPTION
				"MEMORY INDEX"
			::= { blade25MemoryEntry 1 }
		
		b25MEMMark OBJECT-TYPE
			SYNTAX DisplayString
			MAX-ACCESS read-only
			STATUS current
			DESCRIPTION
				"Get the memory silk-screen."
			::= { blade25MemoryEntry 2 }
		
		b25MEMInfo OBJECT-TYPE
			SYNTAX DisplayString
			MAX-ACCESS read-only
			STATUS current
			DESCRIPTION
				"Get the memory description of vendor, frequency and capacity."
			::= { blade25MemoryEntry 3 }
		
		b25MEMPresent OBJECT-TYPE
			SYNTAX INTEGER
			MAX-ACCESS read-only
			STATUS current
			DESCRIPTION
				"Get the memory presence status."
			::= { blade25MemoryEntry 4 }
		
		b25MEMHealth OBJECT-TYPE
			SYNTAX INTEGER
			MAX-ACCESS read-only
			STATUS current
			DESCRIPTION
				"Get the memory health status."
			::= { blade25MemoryEntry 5 }
		
		b25MEMLocation OBJECT-TYPE
			SYNTAX DisplayString
			MAX-ACCESS read-only
			STATUS current
			DESCRIPTION
				"Get the memory location."
			::= { blade25MemoryEntry 6 }
		
		blade25MezzTable OBJECT-TYPE
			SYNTAX SEQUENCE OF Blade25MezzEntry
			MAX-ACCESS not-accessible
			STATUS current
			DESCRIPTION
				"A table containing the list of Blade1 FRU information."
			::= { blade25 2008 }
		
		blade25MezzEntry OBJECT-TYPE
			SYNTAX Blade25MezzEntry
			MAX-ACCESS not-accessible
			STATUS current
			DESCRIPTION
				"Information about a particular current FRU."
			INDEX { b25MezzIndex }
			::= { blade25MezzTable 1 }
		
		Blade25MezzEntry ::=
			SEQUENCE { 
				b25MezzIndex
					INTEGER,
				b25MezzMark
					DisplayString,
				b25MezzInfo
					DisplayString,
				b25MezzPresent
					INTEGER,
				b25MezzHealth
					INTEGER,
				b25MezzLocation
					DisplayString,
				b25MezzMac
					DisplayString
			 }

		b25MezzIndex OBJECT-TYPE
			SYNTAX INTEGER
			MAX-ACCESS not-accessible
			STATUS current
			DESCRIPTION
				"MEZZ INDEX"
			::= { blade25MezzEntry 1 }
		
		b25MezzMark OBJECT-TYPE
			SYNTAX DisplayString
			MAX-ACCESS read-only
			STATUS current
			DESCRIPTION
				"Get the MEZZ silk-screen."
			::= { blade25MezzEntry 2 }
		
		b25MezzInfo OBJECT-TYPE
			SYNTAX DisplayString
			MAX-ACCESS read-only
			STATUS current
			DESCRIPTION
				"Get the MEZZ description of type."
			::= { blade25MezzEntry 3 }
		
		b25MezzPresent OBJECT-TYPE
			SYNTAX INTEGER
			MAX-ACCESS read-only
			STATUS current
			DESCRIPTION
				"Get the MEZZ presence status."
			::= { blade25MezzEntry 4 }
		
		b25MezzHealth OBJECT-TYPE
			SYNTAX INTEGER
			MAX-ACCESS read-only
			STATUS current
			DESCRIPTION
				"Get the MEZZ health status."
			::= { blade25MezzEntry 5 }
		
		b25MezzLocation OBJECT-TYPE
			SYNTAX DisplayString
			MAX-ACCESS read-only
			STATUS current
			DESCRIPTION
				"Get the MEZZ location."
			::= { blade25MezzEntry 6 }
		
		b25MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade25MezzEntry 7 }
		
		blade25DiskTable OBJECT-TYPE
			SYNTAX SEQUENCE OF Blade25DiskEntry
			MAX-ACCESS not-accessible
			STATUS current
			DESCRIPTION
				"A table containing the list of Blade1 FRU information."
			::= { blade25 2009 }
		
		blade25DiskEntry OBJECT-TYPE
			SYNTAX Blade25DiskEntry
			MAX-ACCESS not-accessible
			STATUS current
			DESCRIPTION
				"Information about a particular current FRU."
			INDEX { b25DiskIndex }
			::= { blade25DiskTable 1 }
		
		Blade25DiskEntry ::=
			SEQUENCE { 
				b25DiskIndex
					INTEGER,
				b25DiskMark
					DisplayString,
				b25DiskInfo
					DisplayString,
				b25DiskPresent
					INTEGER,
				b25DiskHealth
					INTEGER,
				b25DiskLocation
					DisplayString
			 }

		b25DiskIndex OBJECT-TYPE
			SYNTAX INTEGER
			MAX-ACCESS not-accessible
			STATUS current
			DESCRIPTION
				"DISK INDEX"
			::= { blade25DiskEntry 1 }
		
		b25DiskMark OBJECT-TYPE
			SYNTAX DisplayString
			MAX-ACCESS read-only
			STATUS current
			DESCRIPTION
				"Get the disk silk-screen."
			::= { blade25DiskEntry 2 }
		
		b25DiskInfo OBJECT-TYPE
			SYNTAX DisplayString
			MAX-ACCESS read-only
			STATUS current
			DESCRIPTION
				"Get the disk description of vendor, capacity and speed."
			::= { blade25DiskEntry 3 }
		
		b25DiskPresent OBJECT-TYPE
			SYNTAX INTEGER
			MAX-ACCESS read-only
			STATUS current
			DESCRIPTION
				"Get the disk presence status."
			::= { blade25DiskEntry 4 }
		
		b25DiskHealth OBJECT-TYPE
			SYNTAX INTEGER
			MAX-ACCESS read-only
			STATUS current
			DESCRIPTION
				"Get the disk health status."
			::= { blade25DiskEntry 5 }
		
		b25DiskLocation OBJECT-TYPE
			SYNTAX DisplayString
			MAX-ACCESS read-only
			STATUS current
			DESCRIPTION
				"Get the disk location."
			::= { blade25DiskEntry 6 }
		
		blade25SecretKvmVmmTable OBJECT-TYPE
			SYNTAX SEQUENCE OF Blade25SecretKvmVmmEntry
			MAX-ACCESS not-accessible
			STATUS current
			DESCRIPTION
				"A table containing the list of Blade25 KVM&VMM secret information."
			::= { blade25 2010 }

		blade25SecretKvmVmmEntry OBJECT-TYPE
			SYNTAX Blade25SecretKvmVmmEntry
			MAX-ACCESS not-accessible
			STATUS current
			DESCRIPTION
				"Information about a particular current KVM&VMM."
			INDEX { b25SecretKvmVmmIndex }
			::= { blade25SecretKvmVmmTable 1 }
		Blade25SecretKvmVmmEntry ::=
			SEQUENCE { 
				b25SecretKvmVmmIndex
					INTEGER,
				b25SecretKvmState
					INTEGER,
				b25SecretVmmState
					INTEGER,
				b25MMSecretVmmKey
					DisplayString,
				b25SecretVmmKey
					DisplayString
			 }
		b25SecretKvmVmmIndex OBJECT-TYPE
			SYNTAX INTEGER
			MAX-ACCESS not-accessible
			STATUS current
			DESCRIPTION
				"KVM&VMM INDEX."
			::= { blade25SecretKvmVmmEntry 1 }
		b25SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade25SecretKvmVmmEntry 2 }
		b25SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade25SecretKvmVmmEntry 3 }
		b25MMSecretVmmKey OBJECT-TYPE
			SYNTAX DisplayString
			MAX-ACCESS read-only
			STATUS current
			DESCRIPTION
				"Get the MM secret VMM key."
			::= { blade25SecretKvmVmmEntry 4 }
		b25SecretVmmKey OBJECT-TYPE
			SYNTAX DisplayString
			MAX-ACCESS read-write
			STATUS current
			DESCRIPTION
				"Set the secret VMM key."
			::= { blade25SecretKvmVmmEntry 5 }
		blade26 OBJECT IDENTIFIER ::= { blades 26 }

		
 		b26DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade26 4 }
		
 		b26PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade26 5 }
		
 		b26Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade26 6 }

		
 		b26Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b14Health information about a particular b14Location. 
				This will be one of the following:
				(0-ok, 1-minor, 2-major, 3-majorandminor,4-critical,5-criticalandminor,6-criticalandmajor,7-criticalandmajorandminor)"
			::= { blade26 8 }
		
 		b26HealthEvents OBJECT-TYPE
			SYNTAX DisplayString
			MAX-ACCESS read-only
			STATUS current
			DESCRIPTION
				"Events that contribute to the b14Health of the b14Location.  
				This is a list of events currently happening on the 
				b14Location."
			::= { blade26 9 }
		
 		b26ClearSEL OBJECT-TYPE
			SYNTAX INTEGER { clear(1) }
			MAX-ACCESS read-write
			STATUS current
			DESCRIPTION
				"Clean the BMC's SEL on the board."
			::= { blade26 12 }
		
 		b26ExDiskBoardPresence OBJECT-TYPE
			SYNTAX INTEGER
				{
				not-present(0),
				present(1)
				}
			MAX-ACCESS read-only
			STATUS current
			DESCRIPTION
				"Used to find out if the extended disk board is present.
				0 - not present
				1 - present"
			::= { blade26 14 }
		
 		b26BladeVersion OBJECT-TYPE
			SYNTAX DisplayString
			MAX-ACCESS read-only
			STATUS current
			DESCRIPTION
				"display the Version of board14."
			::= { blade26 20 }
		
 		b26MACAddress OBJECT-TYPE
			SYNTAX DisplayString
			MAX-ACCESS read-only
			STATUS current
			DESCRIPTION
				"display the MACAddress of board14."
			::= { blade26 21 }
		
				
							
		
 		b26Safepwofftime OBJECT-TYPE
			SYNTAX INTEGER
			MAX-ACCESS read-write
			STATUS current
			DESCRIPTION
				"the safe poweroff time.
				"
			::= { blade26 26 }
		
 		b26BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]   
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]     
				6=Force boot into BIOS Setup
				15=Force boot from Floppy/primary removable media           
				
				"
			::= { blade26 32 }
		
 		b26Systeminfo OBJECT-TYPE
			SYNTAX DisplayString
			MAX-ACCESS read-write
			STATUS current
			DESCRIPTION
				"display the system information of board14."
			::= { blade26 36 }

		
 		b26SystemProperties OBJECT-TYPE
			SYNTAX DisplayString
			MAX-ACCESS read-only
			STATUS current
			DESCRIPTION
				"Get the power of blade1."
			::= { blade26 39 }
		
 		b26BiosCfg OBJECT-TYPE
			SYNTAX DisplayString
			MAX-ACCESS read-write
			STATUS current
			DESCRIPTION
				"Get the power of blade1."
			::= { blade26 40 }
		
 		b26WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade26 41 }
		
 		b26RealTimePower OBJECT-TYPE
			SYNTAX INTEGER
			MAX-ACCESS read-only
			STATUS current
			DESCRIPTION
				" "
			::= { blade26 43 }
		
 		b26PowerCapping OBJECT-TYPE
			SYNTAX DisplayString
			MAX-ACCESS read-write
			STATUS current
			DESCRIPTION
				" "
			::= { blade26 44 }
		
 		b26Powerreference OBJECT-TYPE
			SYNTAX INTEGER
			MAX-ACCESS read-only
			STATUS current
			DESCRIPTION
				" "
			::= { blade26 45 }
		
 		b26ClearBiosConfig OBJECT-TYPE
			SYNTAX INTEGER
			MAX-ACCESS read-write
			STATUS current
			DESCRIPTION
				" "
			::= { blade26 46 }
		
 		b26BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade26 47 }
		
 		b26BmcUserAdd OBJECT-TYPE
			SYNTAX DisplayString
			MAX-ACCESS read-write
			STATUS current
			DESCRIPTION
				"Used to Add the BMC User
				settable format:
				username,passwd"
			::= { blade26 48 }
		
 		b26BmcUserDel OBJECT-TYPE
			SYNTAX DisplayString
			MAX-ACCESS read-write
			STATUS current
			DESCRIPTION
				"Used to Del the BMC User
				settable format:
				username"
			::= { blade26 49 }
		
 		b26BmcUserPasswd OBJECT-TYPE
			SYNTAX DisplayString
			MAX-ACCESS read-write
			STATUS current
			DESCRIPTION
				"Used to Change the BMC User Passwd
				settable format:
				username,passwd"
			::= { blade26 50 }
		
 		b26BmcUserpropertychg OBJECT-TYPE
			SYNTAX DisplayString
			MAX-ACCESS read-write
			STATUS current
			DESCRIPTION
				"Used to Change the BMC User Property
				settable format:
				username,property"
			::= { blade26 51 }
		
 		b26BmcGateway OBJECT-TYPE
			SYNTAX DisplayString
			MAX-ACCESS read-write
			STATUS current
			DESCRIPTION
				"Read or set the gateway."
			::= { blade26 52 }
		
 		b26SlotBitmap OBJECT-TYPE
			SYNTAX INTEGER
			MAX-ACCESS read-only
			STATUS current
			DESCRIPTION
				" "
			::= { blade26 55 }
		
		b26systemGuid OBJECT-TYPE
			SYNTAX DisplayString
			MAX-ACCESS read-only
			STATUS current
			DESCRIPTION
				" "
			::= { blade26 56 }
		
		b26ProductName OBJECT-TYPE
			SYNTAX DisplayString
			MAX-ACCESS read-only
			STATUS current
			DESCRIPTION
				"display the Version of board14."
			::= { blade26 57 }
			
		b26BundleVersion OBJECT-TYPE
			SYNTAX DisplayString
			MAX-ACCESS read-write
			STATUS current
			DESCRIPTION
				"Get or set the board26 bundle version."
			::= { blade26 58 }

 		blade26SensorTargetTable OBJECT-TYPE
			SYNTAX SEQUENCE OF Blade26SensorTargetEntry
			MAX-ACCESS not-accessible
			STATUS current
			DESCRIPTION
				"A table containing the list of sensor information."
			::= { blade26 2001 }
		
 		blade26SensorTargetEntry OBJECT-TYPE
			SYNTAX Blade26SensorTargetEntry
			MAX-ACCESS not-accessible
			STATUS current
			DESCRIPTION
				"Information about a particular current sensor."
			INDEX { b14Target }
			::= { blade26SensorTargetTable 1 }
		
		Blade26SensorTargetEntry ::=
			SEQUENCE { 
				b26Target
					DisplayString,
				b26Current
					DisplayString,
				b26ThresholdsAll
					DisplayString,
				b26UpperCritical
					DisplayString,
				b26UpperNonCritical
					DisplayString,
				b26UpperNonRecoverable
					DisplayString,
				b26LowerNonCritical
					DisplayString,
				b26LowerCritical
					DisplayString,
				b26LowerNonRecoverable
					DisplayString,
				b26SensorHealth
					INTEGER,
				b26SensorHealthEvents
					DisplayString,
				b26NegativeHysteresis
					DisplayString,
				b26PositiveHysteresis
					DisplayString,
				b26SensorType
					DisplayString,
				b26SensorFRUInfo
					DisplayString
			 }

 		b26Target OBJECT-TYPE
			SYNTAX DisplayString
			MAX-ACCESS not-accessible
			STATUS current
			DESCRIPTION
				"sensor Name"
			::= { blade26SensorTargetEntry 1 }
		
 		b26Current OBJECT-TYPE
			SYNTAX DisplayString
			MAX-ACCESS read-only
			STATUS current
			DESCRIPTION
				"Display the current value of a sensor."
			::= { blade26SensorTargetEntry 2 }
		
 		b26ThresholdsAll OBJECT-TYPE
			SYNTAX DisplayString
			MAX-ACCESS read-only
			STATUS current
			DESCRIPTION
				"All thresholds of a sensor"
			::= { blade26SensorTargetEntry 3 }
		
 		b26UpperCritical OBJECT-TYPE
			SYNTAX DisplayString
			MAX-ACCESS read-write
			STATUS current
			DESCRIPTION
				"Upper critical thresholds"
			::= { blade26SensorTargetEntry 4 }
		
 		b26UpperNonCritical OBJECT-TYPE
			SYNTAX DisplayString
			MAX-ACCESS read-write
			STATUS current
			DESCRIPTION
				"Upper non-critical thresholds"
			::= { blade26SensorTargetEntry 5 }
		
 		b26UpperNonRecoverable OBJECT-TYPE
			SYNTAX DisplayString
			MAX-ACCESS read-write
			STATUS current
			DESCRIPTION
				"Upper non-recoverable thresholds"
			::= { blade26SensorTargetEntry 6 }
		
 		b26LowerNonCritical OBJECT-TYPE
			SYNTAX DisplayString
			MAX-ACCESS read-write
			STATUS current
			DESCRIPTION
				"Lower non-critical thresholds"
			::= { blade26SensorTargetEntry 7 }
		
 		b26LowerCritical OBJECT-TYPE
			SYNTAX DisplayString
			MAX-ACCESS read-write
			STATUS current
			DESCRIPTION
				"Lower critical thresholds"
			::= { blade26SensorTargetEntry 8 }
		
 		b26LowerNonRecoverable OBJECT-TYPE
			SYNTAX DisplayString
			MAX-ACCESS read-write
			STATUS current
			DESCRIPTION
				"Lower non-recoverable thresholds"
			::= { blade26SensorTargetEntry 9 }
		
 		b26SensorHealth OBJECT-TYPE
			SYNTAX INTEGER
				{
				ok(0),
				minor(1),
				major(2),
				critical(3)
				}
			MAX-ACCESS read-only
			STATUS current
			DESCRIPTION
				"b14Health information about a particular b14Location. 
				This will be one of the following:
				(0-ok, 1-minor, 2-major, 3-critical)"
			::= { blade26SensorTargetEntry 10 }
		
 		b26SensorHealthEvents OBJECT-TYPE
			SYNTAX DisplayString
			MAX-ACCESS read-only
			STATUS current
			DESCRIPTION
				"Events that contribute to the b14Health of the b14Location.  
				This is a list of events currently happening on the 
				b14Location."
			::= { blade26SensorTargetEntry 11 }
		
		
 		b26NegativeHysteresis OBJECT-TYPE
			SYNTAX DisplayString
			MAX-ACCESS read-write
			STATUS current
			DESCRIPTION
				"Get/Set the negativeHysteresis value"
			::= { blade26SensorTargetEntry 16 }
		
 		b26PositiveHysteresis OBJECT-TYPE
			SYNTAX DisplayString
			MAX-ACCESS read-write
			STATUS current
			DESCRIPTION
				"Get/Set the positiveHysteresis value."
			::= { blade26SensorTargetEntry 17 }
		
 		b26SensorType OBJECT-TYPE
			SYNTAX DisplayString
			MAX-ACCESS read-only
			STATUS current
			DESCRIPTION
				"Get the type of the sensor."
			::= { blade26SensorTargetEntry 18 }
		
 		b26SensorFRUInfo OBJECT-TYPE
			SYNTAX DisplayString
			MAX-ACCESS read-only
			STATUS current
			DESCRIPTION
				"Get the fruinfo of the sensor."
			::= { blade26SensorTargetEntry 19 }
		
 		blade26FruTable OBJECT-TYPE
			SYNTAX SEQUENCE OF Blade26FruEntry
			MAX-ACCESS not-accessible
			STATUS current
			DESCRIPTION
				"A table containing the list of FRU information."
			::= { blade26 2002 }
		
 		blade26FruEntry OBJECT-TYPE
			SYNTAX Blade26FruEntry
			MAX-ACCESS not-accessible
			STATUS current
			DESCRIPTION
				"Information about a particular current FRU."
			INDEX { b14fruNumber }
			::= { blade26FruTable 1 }
		
		Blade26FruEntry ::=
			SEQUENCE { 
				b26fruNumber
					INTEGER,
				b26FruHotSwapState
					DisplayString,
				b26FruLedProperties
					DisplayString,
				b26FRUControl
					INTEGER,
				b26FRULabel
					DisplayString,
				b26ResetReason
					DisplayString
			 }

 		b26fruNumber OBJECT-TYPE
			SYNTAX INTEGER
			MAX-ACCESS not-accessible
			STATUS current
			DESCRIPTION
				" "
			::= { blade26FruEntry 1 }
		
 		b26FruHotSwapState OBJECT-TYPE
			SYNTAX DisplayString
			MAX-ACCESS read-only
			STATUS current
			DESCRIPTION
				"Retrieve the hot swap state of the FRU from the 
				internally known hot swap states of blade14."
			::= { blade26FruEntry 3 }
		
 		b26FruLedProperties OBJECT-TYPE
			SYNTAX DisplayString
			MAX-ACCESS read-only
			STATUS current
			DESCRIPTION
				"Retrieves the LED support information from a FRU. Returns a comma separated
				list of LEDS and the number of FRU supported user LEDs."
			::= { blade26FruEntry 4 }

		

		b26FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade26FruEntry 9 }
		
 		b26FRULabel OBJECT-TYPE
			SYNTAX DisplayString
			MAX-ACCESS read-only
			STATUS current
			DESCRIPTION
				"Get fru label of blade14."
			::= { blade26FruEntry 10 }
		
 		b26ResetReason OBJECT-TYPE
			SYNTAX DisplayString
			MAX-ACCESS read-only
			STATUS current
			DESCRIPTION
				"Delete fru label of smm."
			::= { blade26FruEntry 11 }
		
 		blade26FruLedTable OBJECT-TYPE
			SYNTAX SEQUENCE OF Blade26FruLedEntry
			MAX-ACCESS not-accessible
			STATUS current
			DESCRIPTION
				"A table containing the list of led information."
			::= { blade26 2003 }
		
 		blade26FruLedEntry OBJECT-TYPE
			SYNTAX Blade26FruLedEntry
			MAX-ACCESS not-accessible
			STATUS current
			DESCRIPTION
				"Information about a particular current led."
			INDEX { b14FruID, b14FruLed }
			::= { blade26FruLedTable 1 }
		
		Blade26FruLedEntry ::=
			SEQUENCE { 
				b26FruID
					INTEGER,
				b26FruLed
					DisplayString,
				b26FruLedColorProps
					DisplayString,
				b26FruLedState
					DisplayString
			 }

 		b26FruID OBJECT-TYPE
			SYNTAX INTEGER
			MAX-ACCESS not-accessible
			STATUS current
			DESCRIPTION
				" "
			::= { blade26FruLedEntry 1 }
		
 		b26FruLed OBJECT-TYPE
			SYNTAX DisplayString
			MAX-ACCESS not-accessible
			STATUS current
			DESCRIPTION
				" "
			::= { blade26FruLedEntry 2 }
		
 		b26FruLedColorProps OBJECT-TYPE
			SYNTAX DisplayString
			MAX-ACCESS read-only
			STATUS current
			DESCRIPTION
				"Finds out what colors are supported by the LED"
			::= { blade26FruLedEntry 3 }
		
 		b26FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade26FruLedEntry 4 }
		
 		blade26FruDescriptionTable OBJECT-TYPE
			SYNTAX SEQUENCE OF Blade26FruDescriptionEntry
			MAX-ACCESS not-accessible
			STATUS current
			DESCRIPTION
				"A table containing the list of blade14 FRU information."
			::= { blade26 2004 }
		
 		blade26FruDescriptionEntry OBJECT-TYPE
			SYNTAX Blade26FruDescriptionEntry
			MAX-ACCESS not-accessible
			STATUS current
			DESCRIPTION
				"Information about a particular current FRU."
			INDEX { b14fruNum }
			::= { blade26FruDescriptionTable 1 }
		
		Blade26FruDescriptionEntry ::=
			SEQUENCE { 
				b26fruNum
					INTEGER,
				b26fruBoardDescription
					DisplayString,
				b26fruBoardManufacturer
					DisplayString,
				b26fruBoardPartNumber
					DisplayString,
				b26fruBoardSerialNumber
					DisplayString,
				b26fruBoardManufactureDate
					DisplayString,
				b26fruProductDescription
					DisplayString,
				b26fruProductManufacturer
					DisplayString,
				b26fruProductPartNumber
					DisplayString,
				b26fruProductSerialNumber
					DisplayString,
				b26fruProductRevision
					DisplayString,
				b26fruAll
					DisplayString
			 }

 		b26fruNum OBJECT-TYPE
			SYNTAX INTEGER
			MAX-ACCESS not-accessible
			STATUS current
			DESCRIPTION
				"blade14 FRU's INDEX"
			::= { blade26FruDescriptionEntry 1 }
		
 		b26fruBoardDescription OBJECT-TYPE
			SYNTAX DisplayString
			MAX-ACCESS read-only
			STATUS current
			DESCRIPTION
				"Used to read the Board Description from the blade14 fru."
			::= { blade26FruDescriptionEntry 2 }
		
 		b26fruBoardManufacturer OBJECT-TYPE
			SYNTAX DisplayString
			MAX-ACCESS read-only
			STATUS current
			DESCRIPTION
				"Used to read the Board Manufacturer from the bladef14 fru."
			::= { blade26FruDescriptionEntry 3 }
		
 		b26fruBoardPartNumber OBJECT-TYPE
			SYNTAX DisplayString
			MAX-ACCESS read-only
			STATUS current
			DESCRIPTION
				"Used to read the Board Part Number from the blade14 fru."
			::= { blade26FruDescriptionEntry 4 }
		
 		b26fruBoardSerialNumber OBJECT-TYPE
			SYNTAX DisplayString
			MAX-ACCESS read-only
			STATUS current
			DESCRIPTION
				"Used to read the Board Serial Number from the blade14 fru."
			::= { blade26FruDescriptionEntry 5 }
		
 		b26fruBoardManufactureDate OBJECT-TYPE
			SYNTAX DisplayString
			MAX-ACCESS read-only
			STATUS current
			DESCRIPTION
				"Used to read the Board Manufacture Date from the blade14 fru."
			::= { blade26FruDescriptionEntry 6 }
		
 		b26fruProductDescription OBJECT-TYPE
			SYNTAX DisplayString
			MAX-ACCESS read-only
			STATUS current
			DESCRIPTION
				"Used to read the Product Description from the blade14 fru."
			::= { blade26FruDescriptionEntry 7 }
		
 		b26fruProductManufacturer OBJECT-TYPE
			SYNTAX DisplayString
			MAX-ACCESS read-only
			STATUS current
			DESCRIPTION
				"Used to read the Product Manufacturer from the blade14 fru."
			::= { blade26FruDescriptionEntry 8 }
		
 		b26fruProductPartNumber OBJECT-TYPE
			SYNTAX DisplayString
			MAX-ACCESS read-only
			STATUS current
			DESCRIPTION
				"Used to read the Product Part Number from the blade14 fru."
			::= { blade26FruDescriptionEntry 9 }
		
 		b26fruProductSerialNumber OBJECT-TYPE
			SYNTAX DisplayString
			MAX-ACCESS read-only
			STATUS current
			DESCRIPTION
				"Used to read the Product Serial Number from the blade14 fru."
			::= { blade26FruDescriptionEntry 10 }
		
 		b26fruProductRevision OBJECT-TYPE
			SYNTAX DisplayString
			MAX-ACCESS read-only
			STATUS current
			DESCRIPTION
				"Used to read the Product Revision from the blade14 fru."
			::= { blade26FruDescriptionEntry 13 }
		
 		b26fruAll OBJECT-TYPE
			SYNTAX DisplayString
			MAX-ACCESS read-only
			STATUS current
			DESCRIPTION
				"Used to read the fru info all."
			::= { blade26FruDescriptionEntry 14 }
		
		blade26CPUTable OBJECT-TYPE
			SYNTAX SEQUENCE OF Blade26CPUEntry
			MAX-ACCESS not-accessible
			STATUS current
			DESCRIPTION
				"A table containing the list of Blade1 FRU information."
			::= { blade26 2006 }
		
		blade26CPUEntry OBJECT-TYPE
			SYNTAX Blade26CPUEntry
			MAX-ACCESS not-accessible
			STATUS current
			DESCRIPTION
				"Information about a particular current FRU."
			INDEX { b26CPUIndex }
			::= { blade26CPUTable 1 }
		
		Blade26CPUEntry ::=
			SEQUENCE { 
				b26CPUIndex
					INTEGER,
				b26CPUMark
					DisplayString,
				b26CPUInfo
					DisplayString,
				b26CPUPresent
					INTEGER,
				b26CPUHealth
					INTEGER,
				b26CPULocation
					DisplayString
			 }

		b26CPUIndex OBJECT-TYPE
			SYNTAX INTEGER
			MAX-ACCESS not-accessible
			STATUS current
			DESCRIPTION
				"CPU INDEX"
			::= { blade26CPUEntry 1 }
		
		b26CPUMark OBJECT-TYPE
			SYNTAX DisplayString
			MAX-ACCESS read-only
			STATUS current
			DESCRIPTION
				"Get the CPU silk-screen."
			::= { blade26CPUEntry 2 }
		
		b26CPUInfo OBJECT-TYPE
			SYNTAX DisplayString
			MAX-ACCESS read-only
			STATUS current
			DESCRIPTION
				"Get the CPU description of vendor, type and frequency."
			::= { blade26CPUEntry 3 }
		
		b26CPUPresent OBJECT-TYPE
			SYNTAX INTEGER
			MAX-ACCESS read-only
			STATUS current
			DESCRIPTION
				"Get the CPU presence status."
			::= { blade26CPUEntry 4 }
		
		b26CPUHealth OBJECT-TYPE
			SYNTAX INTEGER
			MAX-ACCESS read-only
			STATUS current
			DESCRIPTION
				"Get the CPU health status."
			::= { blade26CPUEntry 5 }
		
		b26CPULocation OBJECT-TYPE
			SYNTAX DisplayString
			MAX-ACCESS read-only
			STATUS current
			DESCRIPTION
				"Get the CPU location."
			::= { blade26CPUEntry 6 }
		
		blade26MemoryTable OBJECT-TYPE
			SYNTAX SEQUENCE OF Blade26MemoryEntry
			MAX-ACCESS not-accessible
			STATUS current
			DESCRIPTION
				"A table containing the list of Blade1 FRU information."
			::= { blade26 2007 }
		
		blade26MemoryEntry OBJECT-TYPE
			SYNTAX Blade26MemoryEntry
			MAX-ACCESS not-accessible
			STATUS current
			DESCRIPTION
				"Information about a particular current FRU."
			INDEX { b26MEMIndex }
			::= { blade26MemoryTable 1 }
		
		Blade26MemoryEntry ::=
			SEQUENCE { 
				b26MEMIndex
					INTEGER,
				b26MEMMark
					DisplayString,
				b26MEMInfo
					DisplayString,
				b26MEMPresent
					INTEGER,
				b26MEMHealth
					INTEGER,
				b26MEMLocation
					DisplayString
			 }

		b26MEMIndex OBJECT-TYPE
			SYNTAX INTEGER
			MAX-ACCESS not-accessible
			STATUS current
			DESCRIPTION
				"MEMORY INDEX"
			::= { blade26MemoryEntry 1 }
		
		b26MEMMark OBJECT-TYPE
			SYNTAX DisplayString
			MAX-ACCESS read-only
			STATUS current
			DESCRIPTION
				"Get the memory silk-screen."
			::= { blade26MemoryEntry 2 }
		
		b26MEMInfo OBJECT-TYPE
			SYNTAX DisplayString
			MAX-ACCESS read-only
			STATUS current
			DESCRIPTION
				"Get the memory description of vendor, frequency and capacity."
			::= { blade26MemoryEntry 3 }
		
		b26MEMPresent OBJECT-TYPE
			SYNTAX INTEGER
			MAX-ACCESS read-only
			STATUS current
			DESCRIPTION
				"Get the memory presence status."
			::= { blade26MemoryEntry 4 }
		
		b26MEMHealth OBJECT-TYPE
			SYNTAX INTEGER
			MAX-ACCESS read-only
			STATUS current
			DESCRIPTION
				"Get the memory health status."
			::= { blade26MemoryEntry 5 }
		
		b26MEMLocation OBJECT-TYPE
			SYNTAX DisplayString
			MAX-ACCESS read-only
			STATUS current
			DESCRIPTION
				"Get the memory location."
			::= { blade26MemoryEntry 6 }
		
		blade26MezzTable OBJECT-TYPE
			SYNTAX SEQUENCE OF Blade26MezzEntry
			MAX-ACCESS not-accessible
			STATUS current
			DESCRIPTION
				"A table containing the list of Blade1 FRU information."
			::= { blade26 2008 }
		
		blade26MezzEntry OBJECT-TYPE
			SYNTAX Blade26MezzEntry
			MAX-ACCESS not-accessible
			STATUS current
			DESCRIPTION
				"Information about a particular current FRU."
			INDEX { b26MezzIndex }
			::= { blade26MezzTable 1 }
		
		Blade26MezzEntry ::=
			SEQUENCE { 
				b26MezzIndex
					INTEGER,
				b26MezzMark
					DisplayString,
				b26MezzInfo
					DisplayString,
				b26MezzPresent
					INTEGER,
				b26MezzHealth
					INTEGER,
				b26MezzLocation
					DisplayString,
				b26MezzMac
					DisplayString
			 }

		b26MezzIndex OBJECT-TYPE
			SYNTAX INTEGER
			MAX-ACCESS not-accessible
			STATUS current
			DESCRIPTION
				"MEZZ INDEX"
			::= { blade26MezzEntry 1 }
		
		b26MezzMark OBJECT-TYPE
			SYNTAX DisplayString
			MAX-ACCESS read-only
			STATUS current
			DESCRIPTION
				"Get the MEZZ silk-screen."
			::= { blade26MezzEntry 2 }
		
		b26MezzInfo OBJECT-TYPE
			SYNTAX DisplayString
			MAX-ACCESS read-only
			STATUS current
			DESCRIPTION
				"Get the MEZZ description of type."
			::= { blade26MezzEntry 3 }
		
		b26MezzPresent OBJECT-TYPE
			SYNTAX INTEGER
			MAX-ACCESS read-only
			STATUS current
			DESCRIPTION
				"Get the MEZZ presence status."
			::= { blade26MezzEntry 4 }
		
		b26MezzHealth OBJECT-TYPE
			SYNTAX INTEGER
			MAX-ACCESS read-only
			STATUS current
			DESCRIPTION
				"Get the MEZZ health status."
			::= { blade26MezzEntry 5 }
		
		b26MezzLocation OBJECT-TYPE
			SYNTAX DisplayString
			MAX-ACCESS read-only
			STATUS current
			DESCRIPTION
				"Get the MEZZ location."
			::= { blade26MezzEntry 6 }
		
		b26MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade26MezzEntry 7 }
		
		blade26DiskTable OBJECT-TYPE
			SYNTAX SEQUENCE OF Blade26DiskEntry
			MAX-ACCESS not-accessible
			STATUS current
			DESCRIPTION
				"A table containing the list of Blade1 FRU information."
			::= { blade26 2009 }
		
		blade26DiskEntry OBJECT-TYPE
			SYNTAX Blade26DiskEntry
			MAX-ACCESS not-accessible
			STATUS current
			DESCRIPTION
				"Information about a particular current FRU."
			INDEX { b26DiskIndex }
			::= { blade26DiskTable 1 }
		
		Blade26DiskEntry ::=
			SEQUENCE { 
				b26DiskIndex
					INTEGER,
				b26DiskMark
					DisplayString,
				b26DiskInfo
					DisplayString,
				b26DiskPresent
					INTEGER,
				b26DiskHealth
					INTEGER,
				b26DiskLocation
					DisplayString
			 }

		b26DiskIndex OBJECT-TYPE
			SYNTAX INTEGER
			MAX-ACCESS not-accessible
			STATUS current
			DESCRIPTION
				"DISK INDEX"
			::= { blade26DiskEntry 1 }
		
		b26DiskMark OBJECT-TYPE
			SYNTAX DisplayString
			MAX-ACCESS read-only
			STATUS current
			DESCRIPTION
				"Get the disk silk-screen."
			::= { blade26DiskEntry 2 }
		
		b26DiskInfo OBJECT-TYPE
			SYNTAX DisplayString
			MAX-ACCESS read-only
			STATUS current
			DESCRIPTION
				"Get the disk description of vendor, capacity and speed."
			::= { blade26DiskEntry 3 }
		
		b26DiskPresent OBJECT-TYPE
			SYNTAX INTEGER
			MAX-ACCESS read-only
			STATUS current
			DESCRIPTION
				"Get the disk presence status."
			::= { blade26DiskEntry 4 }
		
		b26DiskHealth OBJECT-TYPE
			SYNTAX INTEGER
			MAX-ACCESS read-only
			STATUS current
			DESCRIPTION
				"Get the disk health status."
			::= { blade26DiskEntry 5 }
		
		b26DiskLocation OBJECT-TYPE
			SYNTAX DisplayString
			MAX-ACCESS read-only
			STATUS current
			DESCRIPTION
				"Get the disk location."
			::= { blade26DiskEntry 6 }
		
		blade26SecretKvmVmmTable OBJECT-TYPE
			SYNTAX SEQUENCE OF Blade26SecretKvmVmmEntry
			MAX-ACCESS not-accessible
			STATUS current
			DESCRIPTION
				"A table containing the list of Blade26 KVM&VMM secret information."
			::= { blade26 2010 }

		blade26SecretKvmVmmEntry OBJECT-TYPE
			SYNTAX Blade26SecretKvmVmmEntry
			MAX-ACCESS not-accessible
			STATUS current
			DESCRIPTION
				"Information about a particular current KVM&VMM."
			INDEX { b26SecretKvmVmmIndex }
			::= { blade26SecretKvmVmmTable 1 }
		Blade26SecretKvmVmmEntry ::=
			SEQUENCE { 
				b26SecretKvmVmmIndex
					INTEGER,
				b26SecretKvmState
					INTEGER,
				b26SecretVmmState
					INTEGER,
				b26MMSecretVmmKey
					DisplayString,
				b26SecretVmmKey
					DisplayString
			 }
		b26SecretKvmVmmIndex OBJECT-TYPE
			SYNTAX INTEGER
			MAX-ACCESS not-accessible
			STATUS current
			DESCRIPTION
				"KVM&VMM INDEX."
			::= { blade26SecretKvmVmmEntry 1 }
		b26SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade26SecretKvmVmmEntry 2 }
		b26SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade26SecretKvmVmmEntry 3 }
		b26MMSecretVmmKey OBJECT-TYPE
			SYNTAX DisplayString
			MAX-ACCESS read-only
			STATUS current
			DESCRIPTION
				"Get the MM secret VMM key."
			::= { blade26SecretKvmVmmEntry 4 }
		b26SecretVmmKey OBJECT-TYPE
			SYNTAX DisplayString
			MAX-ACCESS read-write
			STATUS current
			DESCRIPTION
				"Set the secret VMM key."
			::= { blade26SecretKvmVmmEntry 5 }
		blade27 OBJECT IDENTIFIER ::= { blades 27 }

		
 		b27DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade27 4 }
		
 		b27PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade27 5 }
		
 		b27Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade27 6 }

		
 		b27Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade27 8 }
		
 		b27HealthEvents OBJECT-TYPE
			SYNTAX DisplayString
			MAX-ACCESS read-only
			STATUS current
			DESCRIPTION
				"Events that contribute to the b1Health of the b1Location.  
				This is a list of events currently happening on the 
				b1Location."
			::= { blade27 9 }
		
 		b27ClearSEL OBJECT-TYPE
			SYNTAX INTEGER { clear(1) }
			MAX-ACCESS read-write
			STATUS current
			DESCRIPTION
				"Clean the BMC's SEL on the board."
			::= { blade27 12 }
		
 		b27ExDiskBoardPresence OBJECT-TYPE
			SYNTAX INTEGER
				{
				not-present(0),
				present(1)
				}
			MAX-ACCESS read-only
			STATUS current
			DESCRIPTION
				"Used to find out if the extended disk board is present.
				0 - not present
				1 - present"
			::= { blade27 14 }
		
 		b27BladeVersion OBJECT-TYPE
			SYNTAX DisplayString
			MAX-ACCESS read-only
			STATUS current
			DESCRIPTION
				"display the Version of board1."
			::= { blade27 20 }
		
 		b27MACAddress OBJECT-TYPE
			SYNTAX DisplayString
			MAX-ACCESS read-only
			STATUS current
			DESCRIPTION
				"display the MACAddress of board1."
			::= { blade27 21 }
		
				
							
		
 		b27Safepwofftime OBJECT-TYPE
			SYNTAX INTEGER
			MAX-ACCESS read-write
			STATUS current
			DESCRIPTION
				"the safe poweroff time.
				"
			::= { blade27 26 }
		
 		b27BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]  
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]       
				6=Force boot into BIOS Setup
				15=Force boot from Floppy/primary removable media           
				
				"
			::= { blade27 32 }
		
 		b27Systeminfo OBJECT-TYPE
			SYNTAX DisplayString
			MAX-ACCESS read-write
			STATUS current
			DESCRIPTION
				"display the system information of board1."
			::= { blade27 36 }

		
 		b27SystemProperties OBJECT-TYPE
			SYNTAX DisplayString
			MAX-ACCESS read-only
			STATUS current
			DESCRIPTION
				"Get the power of blade1."
			::= { blade27 39 }
		
 		b27BiosCfg OBJECT-TYPE
			SYNTAX DisplayString
			MAX-ACCESS read-write
			STATUS current
			DESCRIPTION
				"Get the power of blade1."
			::= { blade27 40 }
		
 		b27WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade27 41 }
		
 		b27RealTimePower OBJECT-TYPE
			SYNTAX INTEGER
			MAX-ACCESS read-only
			STATUS current
			DESCRIPTION
				" "
			::= { blade27 43 }
		
 		b27PowerCapping OBJECT-TYPE
			SYNTAX DisplayString
			MAX-ACCESS read-write
			STATUS current
			DESCRIPTION
				" "
			::= { blade27 44 }
		
 		b27Powerreference OBJECT-TYPE
			SYNTAX INTEGER
			MAX-ACCESS read-only
			STATUS current
			DESCRIPTION
				" "
			::= { blade27 45 }
		
 		b27ClearBiosConfig OBJECT-TYPE
			SYNTAX INTEGER
			MAX-ACCESS read-write
			STATUS current
			DESCRIPTION
				" "
			::= { blade27 46 }
		
 		b27BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade27 47 }
		
 		b27BmcUserAdd OBJECT-TYPE
			SYNTAX DisplayString
			MAX-ACCESS read-write
			STATUS current
			DESCRIPTION
				"Used to Add the BMC User
				settable format:
				username,passwd"
			::= { blade27 48 }
		
 		b27BmcUserDel OBJECT-TYPE
			SYNTAX DisplayString
			MAX-ACCESS read-write
			STATUS current
			DESCRIPTION
				"Used to Del the BMC User
				settable format:
				username"
			::= { blade27 49 }
		
 		b27BmcUserPasswd OBJECT-TYPE
			SYNTAX DisplayString
			MAX-ACCESS read-write
			STATUS current
			DESCRIPTION
				"Used to Change the BMC User Passwd
				settable format:
				username,passwd"
			::= { blade27 50 }
		
 		b27BmcUserpropertychg OBJECT-TYPE
			SYNTAX DisplayString
			MAX-ACCESS read-write
			STATUS current
			DESCRIPTION
				"Used to Change the BMC User Property
				settable format:
				username,property"
			::= { blade27 51 }
		
 		b27BmcGateway OBJECT-TYPE
			SYNTAX DisplayString
			MAX-ACCESS read-write
			STATUS current
			DESCRIPTION
				"Read or set the gateway."
			::= { blade27 52 }
		
 		b27SlotBitmap OBJECT-TYPE
			SYNTAX INTEGER
			MAX-ACCESS read-only
			STATUS current
			DESCRIPTION
				" "
			::= { blade27 55 }
		
		b27systemGuid OBJECT-TYPE
			SYNTAX DisplayString
			MAX-ACCESS read-only
			STATUS current
			DESCRIPTION
				" "
			::= { blade27 56 }
		
		b27ProductName OBJECT-TYPE
			SYNTAX DisplayString
			MAX-ACCESS read-only
			STATUS current
			DESCRIPTION
				"display the Version of board1."
			::= { blade27 57 }
			
		b27BundleVersion OBJECT-TYPE
			SYNTAX DisplayString
			MAX-ACCESS read-write
			STATUS current
			DESCRIPTION
				"Get or set the board27 bundle version."
			::= { blade27 58 }

 		blade27SensorTargetTable OBJECT-TYPE
			SYNTAX SEQUENCE OF Blade27SensorTargetEntry
			MAX-ACCESS not-accessible
			STATUS current
			DESCRIPTION
				"A table containing the list of sensor information."
			::= { blade27 2001 }
		
 		blade27SensorTargetEntry OBJECT-TYPE
			SYNTAX Blade27SensorTargetEntry
			MAX-ACCESS not-accessible
			STATUS current
			DESCRIPTION
				"Information about a particular current sensor."
			INDEX { b1Target }
			::= { blade27SensorTargetTable 1 }
		
		Blade27SensorTargetEntry ::=
			SEQUENCE { 
				b27Target
					DisplayString,
				b27Current
					DisplayString,
				b27ThresholdsAll
					DisplayString,
				b27UpperCritical
					DisplayString,
				b27UpperNonCritical
					DisplayString,
				b27UpperNonRecoverable
					DisplayString,
				b27LowerNonCritical
					DisplayString,
				b27LowerCritical
					DisplayString,
				b27LowerNonRecoverable
					DisplayString,
				b27SensorHealth
					INTEGER,
				b27SensorHealthEvents
					DisplayString,
				b27NegativeHysteresis
					DisplayString,
				b27PositiveHysteresis
					DisplayString,
				b27SensorType
					DisplayString,
				b27SensorFRUInfo
					DisplayString
			 }

 		b27Target OBJECT-TYPE
			SYNTAX DisplayString
			MAX-ACCESS not-accessible
			STATUS current
			DESCRIPTION
				"sensor Name"
			::= { blade27SensorTargetEntry 1 }
		
 		b27Current OBJECT-TYPE
			SYNTAX DisplayString
			MAX-ACCESS read-only
			STATUS current
			DESCRIPTION
				"Display the current value of a sensor."
			::= { blade27SensorTargetEntry 2 }
		
 		b27ThresholdsAll OBJECT-TYPE
			SYNTAX DisplayString
			MAX-ACCESS read-only
			STATUS current
			DESCRIPTION
				"All thresholds of a sensor"
			::= { blade27SensorTargetEntry 3 }
		
 		b27UpperCritical OBJECT-TYPE
			SYNTAX DisplayString
			MAX-ACCESS read-write
			STATUS current
			DESCRIPTION
				"Upper critical thresholds"
			::= { blade27SensorTargetEntry 4 }
		
 		b27UpperNonCritical OBJECT-TYPE
			SYNTAX DisplayString
			MAX-ACCESS read-write
			STATUS current
			DESCRIPTION
				"Upper non-critical thresholds"
			::= { blade27SensorTargetEntry 5 }
		
 		b27UpperNonRecoverable OBJECT-TYPE
			SYNTAX DisplayString
			MAX-ACCESS read-write
			STATUS current
			DESCRIPTION
				"Upper non-recoverable thresholds"
			::= { blade27SensorTargetEntry 6 }
		
 		b27LowerNonCritical OBJECT-TYPE
			SYNTAX DisplayString
			MAX-ACCESS read-write
			STATUS current
			DESCRIPTION
				"Lower non-critical thresholds"
			::= { blade27SensorTargetEntry 7 }
		
 		b27LowerCritical OBJECT-TYPE
			SYNTAX DisplayString
			MAX-ACCESS read-write
			STATUS current
			DESCRIPTION
				"Lower critical thresholds"
			::= { blade27SensorTargetEntry 8 }
		
 		b27LowerNonRecoverable OBJECT-TYPE
			SYNTAX DisplayString
			MAX-ACCESS read-write
			STATUS current
			DESCRIPTION
				"Lower non-recoverable thresholds"
			::= { blade27SensorTargetEntry 9 }
		
 		b27SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade27SensorTargetEntry 10 }
		
 		b27SensorHealthEvents OBJECT-TYPE
			SYNTAX DisplayString
			MAX-ACCESS read-only
			STATUS current
			DESCRIPTION
				"Events that contribute to the b1Health of the b1Location.  
				This is a list of events currently happening on the 
				b1Location."
			::= { blade27SensorTargetEntry 11 }
		
		
 		b27NegativeHysteresis OBJECT-TYPE
			SYNTAX DisplayString
			MAX-ACCESS read-write
			STATUS current
			DESCRIPTION
				"Get/Set the negativeHysteresis value."
			::= { blade27SensorTargetEntry 16 }
		
 		b27PositiveHysteresis OBJECT-TYPE
			SYNTAX DisplayString
			MAX-ACCESS read-write
			STATUS current
			DESCRIPTION
				"Get/Set the positiveHysteresis value."
			::= { blade27SensorTargetEntry 17 }
		
 		b27SensorType OBJECT-TYPE
			SYNTAX DisplayString
			MAX-ACCESS read-only
			STATUS current
			DESCRIPTION
				"Get the type of the sensor."
			::= { blade27SensorTargetEntry 18 }
		
 		b27SensorFRUInfo OBJECT-TYPE
			SYNTAX DisplayString
			MAX-ACCESS read-only
			STATUS current
			DESCRIPTION
				"Get the fruinfo of the sensor."
			::= { blade27SensorTargetEntry 19 }
		
 		blade27FruTable OBJECT-TYPE
			SYNTAX SEQUENCE OF Blade27FruEntry
			MAX-ACCESS not-accessible
			STATUS current
			DESCRIPTION
				"A table containing the list of FRU information."
			::= { blade27 2002 }
		
 		blade27FruEntry OBJECT-TYPE
			SYNTAX Blade27FruEntry
			MAX-ACCESS not-accessible
			STATUS current
			DESCRIPTION
				"Information about a particular current FRU."
			INDEX { b1fruNumber }
			::= { blade27FruTable 1 }
		
		Blade27FruEntry ::=
			SEQUENCE { 
				b27fruNumber
					INTEGER,
				b27FruHotSwapState
					DisplayString,
				b27FruLedProperties
					DisplayString,
				b27FRUControl
					INTEGER,
				b27FRULabel
					DisplayString,
				b27ResetReason
					DisplayString
			 }

 		b27fruNumber OBJECT-TYPE
			SYNTAX INTEGER
			MAX-ACCESS not-accessible
			STATUS current
			DESCRIPTION
				" "
			::= { blade27FruEntry 1 }
		
 		b27FruHotSwapState OBJECT-TYPE
			SYNTAX DisplayString
			MAX-ACCESS read-only
			STATUS current
			DESCRIPTION
				"Retrieve the hot swap state of the FRU from the 
				internally known hot swap states of blade1."
			::= { blade27FruEntry 3 }
		
 		b27FruLedProperties OBJECT-TYPE
			SYNTAX DisplayString
			MAX-ACCESS read-only
			STATUS current
			DESCRIPTION
				"Retrieves the LED support information from a FRU. Returns a comma separated
				list of LEDS and the number of FRU supported user LEDs."
			::= { blade27FruEntry 4 }

		

		b27FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade27FruEntry 9 }
		
 		b27FRULabel OBJECT-TYPE
			SYNTAX DisplayString
			MAX-ACCESS read-only
			STATUS current
			DESCRIPTION
				"Get fru label of blade1."
			::= { blade27FruEntry 10 }
		
 		b27ResetReason OBJECT-TYPE
			SYNTAX DisplayString
			MAX-ACCESS read-only
			STATUS current
			DESCRIPTION
				"Delete fru label of smm."
			::= { blade27FruEntry 11 }
		
 		blade27FruLedTable OBJECT-TYPE
			SYNTAX SEQUENCE OF Blade27FruLedEntry
			MAX-ACCESS not-accessible
			STATUS current
			DESCRIPTION
				"A table containing the list of led information."
			::= { blade27 2003 }
		
 		blade27FruLedEntry OBJECT-TYPE
			SYNTAX Blade27FruLedEntry
			MAX-ACCESS not-accessible
			STATUS current
			DESCRIPTION
				"Information about a particular current led."
			INDEX { b1FruID, b1FruLed }
			::= { blade27FruLedTable 1 }
		
		Blade27FruLedEntry ::=
			SEQUENCE { 
				b27FruID
					INTEGER,
				b27FruLed
					DisplayString,
				b27FruLedColorProps
					DisplayString,
				b27FruLedState
					DisplayString
			 }

 		b27FruID OBJECT-TYPE
			SYNTAX INTEGER
			MAX-ACCESS not-accessible
			STATUS current
			DESCRIPTION
				" "
			::= { blade27FruLedEntry 1 }
		
 		b27FruLed OBJECT-TYPE
			SYNTAX DisplayString
			MAX-ACCESS not-accessible
			STATUS current
			DESCRIPTION
				" "
			::= { blade27FruLedEntry 2 }
		
 		b27FruLedColorProps OBJECT-TYPE
			SYNTAX DisplayString
			MAX-ACCESS read-only
			STATUS current
			DESCRIPTION
				"Finds out what colors are supported by the LED"
			::= { blade27FruLedEntry 3 }
		
 		b27FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade27FruLedEntry 4 }
		
 		blade27FruDescriptionTable OBJECT-TYPE
			SYNTAX SEQUENCE OF Blade27FruDescriptionEntry
			MAX-ACCESS not-accessible
			STATUS current
			DESCRIPTION
				"A table containing the list of Blade1 FRU information."
			::= { blade27 2004 }
		
 		blade27FruDescriptionEntry OBJECT-TYPE
			SYNTAX Blade27FruDescriptionEntry
			MAX-ACCESS not-accessible
			STATUS current
			DESCRIPTION
				"Information about a particular current FRU."
			INDEX { b1fruNum }
			::= { blade27FruDescriptionTable 1 }
		
		Blade27FruDescriptionEntry ::=
			SEQUENCE { 
				b27fruNum
					INTEGER,
				b27fruBoardDescription
					DisplayString,
				b27fruBoardManufacturer
					DisplayString,
				b27fruBoardPartNumber
					DisplayString,
				b27fruBoardSerialNumber
					DisplayString,
				b27fruBoardManufactureDate
					DisplayString,
				b27fruProductDescription
					DisplayString,
				b27fruProductManufacturer
					DisplayString,
				b27fruProductPartNumber
					DisplayString,
				b27fruProductSerialNumber
					DisplayString,
				b27fruProductRevision
					DisplayString,
				b27fruAll
					DisplayString
			 }

 		b27fruNum OBJECT-TYPE
			SYNTAX INTEGER
			MAX-ACCESS not-accessible
			STATUS current
			DESCRIPTION
				"blade1 FRU's INDEX"
			::= { blade27FruDescriptionEntry 1 }
		
 		b27fruBoardDescription OBJECT-TYPE
			SYNTAX DisplayString
			MAX-ACCESS read-only
			STATUS current
			DESCRIPTION
				"Used to read the Board Description from the blade1 fru."
			::= { blade27FruDescriptionEntry 2 }
		
 		b27fruBoardManufacturer OBJECT-TYPE
			SYNTAX DisplayString
			MAX-ACCESS read-only
			STATUS current
			DESCRIPTION
				"Used to read the Board Manufacturer from the blade1 fru."
			::= { blade27FruDescriptionEntry 3 }
		
 		b27fruBoardPartNumber OBJECT-TYPE
			SYNTAX DisplayString
			MAX-ACCESS read-only
			STATUS current
			DESCRIPTION
				"Used to read the Board Part Number from the blade1 fru."
			::= { blade27FruDescriptionEntry 4 }
		
 		b27fruBoardSerialNumber OBJECT-TYPE
			SYNTAX DisplayString
			MAX-ACCESS read-only
			STATUS current
			DESCRIPTION
				"Used to read the Board Serial Number from the blade1 fru."
			::= { blade27FruDescriptionEntry 5 }
		
 		b27fruBoardManufactureDate OBJECT-TYPE
			SYNTAX DisplayString
			MAX-ACCESS read-only
			STATUS current
			DESCRIPTION
				"Used to read the Board Manufacture Date from the blade1 fru."
			::= { blade27FruDescriptionEntry 6 }
		
 		b27fruProductDescription OBJECT-TYPE
			SYNTAX DisplayString
			MAX-ACCESS read-only
			STATUS current
			DESCRIPTION
				"Used to read the Product Description from the blade1 fru."
			::= { blade27FruDescriptionEntry 7 }
		
 		b27fruProductManufacturer OBJECT-TYPE
			SYNTAX DisplayString
			MAX-ACCESS read-only
			STATUS current
			DESCRIPTION
				"Used to read the Product Manufacturer from the blade1 fru."
			::= { blade27FruDescriptionEntry 8 }
		
 		b27fruProductPartNumber OBJECT-TYPE
			SYNTAX DisplayString
			MAX-ACCESS read-only
			STATUS current
			DESCRIPTION
				"Used to read the Product Part Number from the blade1 fru."
			::= { blade27FruDescriptionEntry 9 }
		
 		b27fruProductSerialNumber OBJECT-TYPE
			SYNTAX DisplayString
			MAX-ACCESS read-only
			STATUS current
			DESCRIPTION
				"Used to read the Product Serial Number from the blade1 fru."
			::= { blade27FruDescriptionEntry 10 }
		
 		b27fruProductRevision OBJECT-TYPE
			SYNTAX DisplayString
			MAX-ACCESS read-only
			STATUS current
			DESCRIPTION
				"Used to read the Product Revision from the blade1 fru."
			::= { blade27FruDescriptionEntry 13 }
		
 		b27fruAll OBJECT-TYPE
			SYNTAX DisplayString
			MAX-ACCESS read-only
			STATUS current
			DESCRIPTION
				"Used to read the fru info all."
			::= { blade27FruDescriptionEntry 14 }
		
		blade27CPUTable OBJECT-TYPE
			SYNTAX SEQUENCE OF Blade27CPUEntry
			MAX-ACCESS not-accessible
			STATUS current
			DESCRIPTION
				"A table containing the list of Blade1 FRU information."
			::= { blade27 2006 }
		
		blade27CPUEntry OBJECT-TYPE
			SYNTAX Blade27CPUEntry
			MAX-ACCESS not-accessible
			STATUS current
			DESCRIPTION
				"Information about a particular current FRU."
			INDEX { b27CPUIndex }
			::= { blade27CPUTable 1 }
		
		Blade27CPUEntry ::=
			SEQUENCE { 
				b27CPUIndex
					INTEGER,
				b27CPUMark
					DisplayString,
				b27CPUInfo
					DisplayString,
				b27CPUPresent
					INTEGER,
				b27CPUHealth
					INTEGER,
				b27CPULocation
					DisplayString
			 }

		b27CPUIndex OBJECT-TYPE
			SYNTAX INTEGER
			MAX-ACCESS not-accessible
			STATUS current
			DESCRIPTION
				"CPU INDEX"
			::= { blade27CPUEntry 1 }
		
		b27CPUMark OBJECT-TYPE
			SYNTAX DisplayString
			MAX-ACCESS read-only
			STATUS current
			DESCRIPTION
				"Get the CPU silk-screen."
			::= { blade27CPUEntry 2 }
		
		b27CPUInfo OBJECT-TYPE
			SYNTAX DisplayString
			MAX-ACCESS read-only
			STATUS current
			DESCRIPTION
				"Get the CPU description of vendor, type and frequency."
			::= { blade27CPUEntry 3 }
		
		b27CPUPresent OBJECT-TYPE
			SYNTAX INTEGER
			MAX-ACCESS read-only
			STATUS current
			DESCRIPTION
				"Get the CPU presence status."
			::= { blade27CPUEntry 4 }
		
		b27CPUHealth OBJECT-TYPE
			SYNTAX INTEGER
			MAX-ACCESS read-only
			STATUS current
			DESCRIPTION
				"Get the CPU health status."
			::= { blade27CPUEntry 5 }
		
		b27CPULocation OBJECT-TYPE
			SYNTAX DisplayString
			MAX-ACCESS read-only
			STATUS current
			DESCRIPTION
				"Get the CPU location."
			::= { blade27CPUEntry 6 }
		
		blade27MemoryTable OBJECT-TYPE
			SYNTAX SEQUENCE OF Blade27MemoryEntry
			MAX-ACCESS not-accessible
			STATUS current
			DESCRIPTION
				"A table containing the list of Blade1 FRU information."
			::= { blade27 2007 }
		
		blade27MemoryEntry OBJECT-TYPE
			SYNTAX Blade27MemoryEntry
			MAX-ACCESS not-accessible
			STATUS current
			DESCRIPTION
				"Information about a particular current FRU."
			INDEX { b27MEMIndex }
			::= { blade27MemoryTable 1 }
		
		Blade27MemoryEntry ::=
			SEQUENCE { 
				b27MEMIndex
					INTEGER,
				b27MEMMark
					DisplayString,
				b27MEMInfo
					DisplayString,
				b27MEMPresent
					INTEGER,
				b27MEMHealth
					INTEGER,
				b27MEMLocation
					DisplayString
			 }

		b27MEMIndex OBJECT-TYPE
			SYNTAX INTEGER
			MAX-ACCESS not-accessible
			STATUS current
			DESCRIPTION
				"MEMORY INDEX"
			::= { blade27MemoryEntry 1 }
		
		b27MEMMark OBJECT-TYPE
			SYNTAX DisplayString
			MAX-ACCESS read-only
			STATUS current
			DESCRIPTION
				"Get the memory silk-screen."
			::= { blade27MemoryEntry 2 }
		
		b27MEMInfo OBJECT-TYPE
			SYNTAX DisplayString
			MAX-ACCESS read-only
			STATUS current
			DESCRIPTION
				"Get the memory description of vendor, frequency and capacity."
			::= { blade27MemoryEntry 3 }
		
		b27MEMPresent OBJECT-TYPE
			SYNTAX INTEGER
			MAX-ACCESS read-only
			STATUS current
			DESCRIPTION
				"Get the memory presence status."
			::= { blade27MemoryEntry 4 }
		
		b27MEMHealth OBJECT-TYPE
			SYNTAX INTEGER
			MAX-ACCESS read-only
			STATUS current
			DESCRIPTION
				"Get the memory health status."
			::= { blade27MemoryEntry 5 }
		
		b27MEMLocation OBJECT-TYPE
			SYNTAX DisplayString
			MAX-ACCESS read-only
			STATUS current
			DESCRIPTION
				"Get the memory location."
			::= { blade27MemoryEntry 6 }
		
		blade27MezzTable OBJECT-TYPE
			SYNTAX SEQUENCE OF Blade27MezzEntry
			MAX-ACCESS not-accessible
			STATUS current
			DESCRIPTION
				"A table containing the list of Blade1 FRU information."
			::= { blade27 2008 }
		
		blade27MezzEntry OBJECT-TYPE
			SYNTAX Blade27MezzEntry
			MAX-ACCESS not-accessible
			STATUS current
			DESCRIPTION
				"Information about a particular current FRU."
			INDEX { b27MezzIndex }
			::= { blade27MezzTable 1 }
		
		Blade27MezzEntry ::=
			SEQUENCE { 
				b27MezzIndex
					INTEGER,
				b27MezzMark
					DisplayString,
				b27MezzInfo
					DisplayString,
				b27MezzPresent
					INTEGER,
				b27MezzHealth
					INTEGER,
				b27MezzLocation
					DisplayString,
				b27MezzMac
					DisplayString
			 }

		b27MezzIndex OBJECT-TYPE
			SYNTAX INTEGER
			MAX-ACCESS not-accessible
			STATUS current
			DESCRIPTION
				"MEZZ INDEX"
			::= { blade27MezzEntry 1 }
		
		b27MezzMark OBJECT-TYPE
			SYNTAX DisplayString
			MAX-ACCESS read-only
			STATUS current
			DESCRIPTION
				"Get the MEZZ silk-screen."
			::= { blade27MezzEntry 2 }
		
		b27MezzInfo OBJECT-TYPE
			SYNTAX DisplayString
			MAX-ACCESS read-only
			STATUS current
			DESCRIPTION
				"Get the MEZZ description of type."
			::= { blade27MezzEntry 3 }
		
		b27MezzPresent OBJECT-TYPE
			SYNTAX INTEGER
			MAX-ACCESS read-only
			STATUS current
			DESCRIPTION
				"Get the MEZZ presence status."
			::= { blade27MezzEntry 4 }
		
		b27MezzHealth OBJECT-TYPE
			SYNTAX INTEGER
			MAX-ACCESS read-only
			STATUS current
			DESCRIPTION
				"Get the MEZZ health status."
			::= { blade27MezzEntry 5 }
		
		b27MezzLocation OBJECT-TYPE
			SYNTAX DisplayString
			MAX-ACCESS read-only
			STATUS current
			DESCRIPTION
				"Get the MEZZ location."
			::= { blade27MezzEntry 6 }
		
		b27MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade27MezzEntry 7 }
		
		blade27DiskTable OBJECT-TYPE
			SYNTAX SEQUENCE OF Blade27DiskEntry
			MAX-ACCESS not-accessible
			STATUS current
			DESCRIPTION
				"A table containing the list of Blade1 FRU information."
			::= { blade27 2009 }
		
		blade27DiskEntry OBJECT-TYPE
			SYNTAX Blade27DiskEntry
			MAX-ACCESS not-accessible
			STATUS current
			DESCRIPTION
				"Information about a particular current FRU."
			INDEX { b27DiskIndex }
			::= { blade27DiskTable 1 }
		
		Blade27DiskEntry ::=
			SEQUENCE { 
				b27DiskIndex
					INTEGER,
				b27DiskMark
					DisplayString,
				b27DiskInfo
					DisplayString,
				b27DiskPresent
					INTEGER,
				b27DiskHealth
					INTEGER,
				b27DiskLocation
					DisplayString
			 }

		b27DiskIndex OBJECT-TYPE
			SYNTAX INTEGER
			MAX-ACCESS not-accessible
			STATUS current
			DESCRIPTION
				"DISK INDEX"
			::= { blade27DiskEntry 1 }
		
		b27DiskMark OBJECT-TYPE
			SYNTAX DisplayString
			MAX-ACCESS read-only
			STATUS current
			DESCRIPTION
				"Get the disk silk-screen."
			::= { blade27DiskEntry 2 }
		
		b27DiskInfo OBJECT-TYPE
			SYNTAX DisplayString
			MAX-ACCESS read-only
			STATUS current
			DESCRIPTION
				"Get the disk description of vendor, capacity and speed."
			::= { blade27DiskEntry 3 }
		
		b27DiskPresent OBJECT-TYPE
			SYNTAX INTEGER
			MAX-ACCESS read-only
			STATUS current
			DESCRIPTION
				"Get the disk presence status."
			::= { blade27DiskEntry 4 }
		
		b27DiskHealth OBJECT-TYPE
			SYNTAX INTEGER
			MAX-ACCESS read-only
			STATUS current
			DESCRIPTION
				"Get the disk health status."
			::= { blade27DiskEntry 5 }
		
		b27DiskLocation OBJECT-TYPE
			SYNTAX DisplayString
			MAX-ACCESS read-only
			STATUS current
			DESCRIPTION
				"Get the disk location."
			::= { blade27DiskEntry 6 }
		
		blade27SecretKvmVmmTable OBJECT-TYPE
			SYNTAX SEQUENCE OF Blade27SecretKvmVmmEntry
			MAX-ACCESS not-accessible
			STATUS current
			DESCRIPTION
				"A table containing the list of Blade27 KVM&VMM secret information."
			::= { blade27 2010 }

		blade27SecretKvmVmmEntry OBJECT-TYPE
			SYNTAX Blade27SecretKvmVmmEntry
			MAX-ACCESS not-accessible
			STATUS current
			DESCRIPTION
				"Information about a particular current KVM&VMM."
			INDEX { b27SecretKvmVmmIndex }
			::= { blade27SecretKvmVmmTable 1 }
		Blade27SecretKvmVmmEntry ::=
			SEQUENCE { 
				b27SecretKvmVmmIndex
					INTEGER,
				b27SecretKvmState
					INTEGER,
				b27SecretVmmState
					INTEGER,
				b27MMSecretVmmKey
					DisplayString,
				b27SecretVmmKey
					DisplayString
			 }
		b27SecretKvmVmmIndex OBJECT-TYPE
			SYNTAX INTEGER
			MAX-ACCESS not-accessible
			STATUS current
			DESCRIPTION
				"KVM&VMM INDEX."
			::= { blade27SecretKvmVmmEntry 1 }
		b27SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade27SecretKvmVmmEntry 2 }
		b27SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade27SecretKvmVmmEntry 3 }
		b27MMSecretVmmKey OBJECT-TYPE
			SYNTAX DisplayString
			MAX-ACCESS read-only
			STATUS current
			DESCRIPTION
				"Get the MM secret VMM key."
			::= { blade27SecretKvmVmmEntry 4 }
		b27SecretVmmKey OBJECT-TYPE
			SYNTAX DisplayString
			MAX-ACCESS read-write
			STATUS current
			DESCRIPTION
				"Set the secret VMM key."
			::= { blade27SecretKvmVmmEntry 5 }
		blade28 OBJECT IDENTIFIER ::= { blades 28 }

		
 		b28DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade28 4 }
		
 		b28PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade28 5 }
		
 		b28Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade28 6 }

		
 		b28Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade28 8 }
		
 		b28HealthEvents OBJECT-TYPE
			SYNTAX DisplayString
			MAX-ACCESS read-only
			STATUS current
			DESCRIPTION
				"Events that contribute to the b1Health of the b1Location.  
				This is a list of events currently happening on the 
				b1Location."
			::= { blade28 9 }
		
 		b28ClearSEL OBJECT-TYPE
			SYNTAX INTEGER { clear(1) }
			MAX-ACCESS read-write
			STATUS current
			DESCRIPTION
				"Clean the BMC's SEL on the board."
			::= { blade28 12 }
		
 		b28ExDiskBoardPresence OBJECT-TYPE
			SYNTAX INTEGER
				{
				not-present(0),
				present(1)
				}
			MAX-ACCESS read-only
			STATUS current
			DESCRIPTION
				"Used to find out if the extended disk board is present.
				0 - not present
				1 - present"
			::= { blade28 14 }
		
 		b28BladeVersion OBJECT-TYPE
			SYNTAX DisplayString
			MAX-ACCESS read-only
			STATUS current
			DESCRIPTION
				"display the Version of board1."
			::= { blade28 20 }
		
 		b28MACAddress OBJECT-TYPE
			SYNTAX DisplayString
			MAX-ACCESS read-only
			STATUS current
			DESCRIPTION
				"display the MACAddress of board1."
			::= { blade28 21 }
		
				
							
		
 		b28Safepwofftime OBJECT-TYPE
			SYNTAX INTEGER
			MAX-ACCESS read-write
			STATUS current
			DESCRIPTION
				"the safe poweroff time.
				"
			::= { blade28 26 }
		
 		b28BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]       
				6=Force boot into BIOS Setup
				15=Force boot from Floppy/primary removable media           
				
				"
			::= { blade28 32 }
		
 		b28Systeminfo OBJECT-TYPE
			SYNTAX DisplayString
			MAX-ACCESS read-write
			STATUS current
			DESCRIPTION
				"display the system information of board1."
			::= { blade28 36 }

		
 		b28SystemProperties OBJECT-TYPE
			SYNTAX DisplayString
			MAX-ACCESS read-only
			STATUS current
			DESCRIPTION
				"Get the power of blade1."
			::= { blade28 39 }
		
 		b28BiosCfg OBJECT-TYPE
			SYNTAX DisplayString
			MAX-ACCESS read-write
			STATUS current
			DESCRIPTION
				"Get the power of blade1."
			::= { blade28 40 }
		
 		b28WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade28 41 }
		
 		b28RealTimePower OBJECT-TYPE
			SYNTAX INTEGER
			MAX-ACCESS read-only
			STATUS current
			DESCRIPTION
				" "
			::= { blade28 43 }
		
 		b28PowerCapping OBJECT-TYPE
			SYNTAX DisplayString
			MAX-ACCESS read-write
			STATUS current
			DESCRIPTION
				" "
			::= { blade28 44 }
		
 		b28Powerreference OBJECT-TYPE
			SYNTAX INTEGER
			MAX-ACCESS read-only
			STATUS current
			DESCRIPTION
				" "
			::= { blade28 45 }
		
 		b28ClearBiosConfig OBJECT-TYPE
			SYNTAX INTEGER
			MAX-ACCESS read-write
			STATUS current
			DESCRIPTION
				" "
			::= { blade28 46 }
		
 		b28BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade28 47 }
		
 		b28BmcUserAdd OBJECT-TYPE
			SYNTAX DisplayString
			MAX-ACCESS read-write
			STATUS current
			DESCRIPTION
				"Used to Add the BMC User
				settable format:
				username,passwd"
			::= { blade28 48 }
		
 		b28BmcUserDel OBJECT-TYPE
			SYNTAX DisplayString
			MAX-ACCESS read-write
			STATUS current
			DESCRIPTION
				"Used to Del the BMC User
				settable format:
				username"
			::= { blade28 49 }
		
 		b28BmcUserPasswd OBJECT-TYPE
			SYNTAX DisplayString
			MAX-ACCESS read-write
			STATUS current
			DESCRIPTION
				"Used to Change the BMC User Passwd
				settable format:
				username,passwd"
			::= { blade28 50 }
		
 		b28BmcUserpropertychg OBJECT-TYPE
			SYNTAX DisplayString
			MAX-ACCESS read-write
			STATUS current
			DESCRIPTION
				"Used to Change the BMC User Property
				settable format:
				username,property"
			::= { blade28 51 }
		
 		b28BmcGateway OBJECT-TYPE
			SYNTAX DisplayString
			MAX-ACCESS read-write
			STATUS current
			DESCRIPTION
				"Read or set the gateway."
			::= { blade28 52 }
		
 		b28SlotBitmap OBJECT-TYPE
			SYNTAX INTEGER
			MAX-ACCESS read-only
			STATUS current
			DESCRIPTION
				" "
			::= { blade28 55 }
		
		b28systemGuid OBJECT-TYPE
			SYNTAX DisplayString
			MAX-ACCESS read-only
			STATUS current
			DESCRIPTION
				" "
			::= { blade28 56 }
		
		b28ProductName OBJECT-TYPE
			SYNTAX DisplayString
			MAX-ACCESS read-only
			STATUS current
			DESCRIPTION
				"display the Version of board1."
			::= { blade28 57 }
			
		b28BundleVersion OBJECT-TYPE
			SYNTAX DisplayString
			MAX-ACCESS read-write
			STATUS current
			DESCRIPTION
				"Get or set the board28 bundle version."
			::= { blade28 58 }

 		blade28SensorTargetTable OBJECT-TYPE
			SYNTAX SEQUENCE OF Blade28SensorTargetEntry
			MAX-ACCESS not-accessible
			STATUS current
			DESCRIPTION
				"A table containing the list of sensor information."
			::= { blade28 2001 }
		
 		blade28SensorTargetEntry OBJECT-TYPE
			SYNTAX Blade28SensorTargetEntry
			MAX-ACCESS not-accessible
			STATUS current
			DESCRIPTION
				"Information about a particular current sensor."
			INDEX { b1Target }
			::= { blade28SensorTargetTable 1 }
		
		Blade28SensorTargetEntry ::=
			SEQUENCE { 
				b28Target
					DisplayString,
				b28Current
					DisplayString,
				b28ThresholdsAll
					DisplayString,
				b28UpperCritical
					DisplayString,
				b28UpperNonCritical
					DisplayString,
				b28UpperNonRecoverable
					DisplayString,
				b28LowerNonCritical
					DisplayString,
				b28LowerCritical
					DisplayString,
				b28LowerNonRecoverable
					DisplayString,
				b28SensorHealth
					INTEGER,
				b28SensorHealthEvents
					DisplayString,
				b28NegativeHysteresis
					DisplayString,
				b28PositiveHysteresis
					DisplayString,
				b28SensorType
					DisplayString,
				b28SensorFRUInfo
					DisplayString
			 }

 		b28Target OBJECT-TYPE
			SYNTAX DisplayString
			MAX-ACCESS not-accessible
			STATUS current
			DESCRIPTION
				"sensor Name"
			::= { blade28SensorTargetEntry 1 }
		
 		b28Current OBJECT-TYPE
			SYNTAX DisplayString
			MAX-ACCESS read-only
			STATUS current
			DESCRIPTION
				"Display the current value of a sensor."
			::= { blade28SensorTargetEntry 2 }
		
 		b28ThresholdsAll OBJECT-TYPE
			SYNTAX DisplayString
			MAX-ACCESS read-only
			STATUS current
			DESCRIPTION
				"All thresholds of a sensor"
			::= { blade28SensorTargetEntry 3 }
		
 		b28UpperCritical OBJECT-TYPE
			SYNTAX DisplayString
			MAX-ACCESS read-write
			STATUS current
			DESCRIPTION
				"Upper critical thresholds"
			::= { blade28SensorTargetEntry 4 }
		
 		b28UpperNonCritical OBJECT-TYPE
			SYNTAX DisplayString
			MAX-ACCESS read-write
			STATUS current
			DESCRIPTION
				"Upper non-critical thresholds"
			::= { blade28SensorTargetEntry 5 }
		
 		b28UpperNonRecoverable OBJECT-TYPE
			SYNTAX DisplayString
			MAX-ACCESS read-write
			STATUS current
			DESCRIPTION
				"Upper non-recoverable thresholds"
			::= { blade28SensorTargetEntry 6 }
		
 		b28LowerNonCritical OBJECT-TYPE
			SYNTAX DisplayString
			MAX-ACCESS read-write
			STATUS current
			DESCRIPTION
				"Lower non-critical thresholds"
			::= { blade28SensorTargetEntry 7 }
		
 		b28LowerCritical OBJECT-TYPE
			SYNTAX DisplayString
			MAX-ACCESS read-write
			STATUS current
			DESCRIPTION
				"Lower critical thresholds"
			::= { blade28SensorTargetEntry 8 }
		
 		b28LowerNonRecoverable OBJECT-TYPE
			SYNTAX DisplayString
			MAX-ACCESS read-write
			STATUS current
			DESCRIPTION
				"Lower non-recoverable thresholds"
			::= { blade28SensorTargetEntry 9 }
		
 		b28SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade28SensorTargetEntry 10 }
		
 		b28SensorHealthEvents OBJECT-TYPE
			SYNTAX DisplayString
			MAX-ACCESS read-only
			STATUS current
			DESCRIPTION
				"Events that contribute to the b1Health of the b1Location.  
				This is a list of events currently happening on the 
				b1Location."
			::= { blade28SensorTargetEntry 11 }
		
		
 		b28NegativeHysteresis OBJECT-TYPE
			SYNTAX DisplayString
			MAX-ACCESS read-write
			STATUS current
			DESCRIPTION
				"Get/Set the negativeHysteresis value."
			::= { blade28SensorTargetEntry 16 }
		
 		b28PositiveHysteresis OBJECT-TYPE
			SYNTAX DisplayString
			MAX-ACCESS read-write
			STATUS current
			DESCRIPTION
				"Get/Set the positiveHysteresis value."
			::= { blade28SensorTargetEntry 17 }
		
 		b28SensorType OBJECT-TYPE
			SYNTAX DisplayString
			MAX-ACCESS read-only
			STATUS current
			DESCRIPTION
				"Get the type of the sensor."
			::= { blade28SensorTargetEntry 18 }
		
 		b28SensorFRUInfo OBJECT-TYPE
			SYNTAX DisplayString
			MAX-ACCESS read-only
			STATUS current
			DESCRIPTION
				"Get the fruinfo of the sensor."
			::= { blade28SensorTargetEntry 19 }
		
 		blade28FruTable OBJECT-TYPE
			SYNTAX SEQUENCE OF Blade28FruEntry
			MAX-ACCESS not-accessible
			STATUS current
			DESCRIPTION
				"A table containing the list of FRU information."
			::= { blade28 2002 }
		
 		blade28FruEntry OBJECT-TYPE
			SYNTAX Blade28FruEntry
			MAX-ACCESS not-accessible
			STATUS current
			DESCRIPTION
				"Information about a particular current FRU."
			INDEX { b1fruNumber }
			::= { blade28FruTable 1 }
		
		Blade28FruEntry ::=
			SEQUENCE { 
				b28fruNumber
					INTEGER,
				b28FruHotSwapState
					DisplayString,
				b28FruLedProperties
					DisplayString,
				b28FRUControl
					INTEGER,
				b28FRULabel
					DisplayString,
				b28ResetReason
					DisplayString
			 }

 		b28fruNumber OBJECT-TYPE
			SYNTAX INTEGER
			MAX-ACCESS not-accessible
			STATUS current
			DESCRIPTION
				" "
			::= { blade28FruEntry 1 }
		
 		b28FruHotSwapState OBJECT-TYPE
			SYNTAX DisplayString
			MAX-ACCESS read-only
			STATUS current
			DESCRIPTION
				"Retrieve the hot swap state of the FRU from the 
				internally known hot swap states of blade1."
			::= { blade28FruEntry 3 }
		
 		b28FruLedProperties OBJECT-TYPE
			SYNTAX DisplayString
			MAX-ACCESS read-only
			STATUS current
			DESCRIPTION
				"Retrieves the LED support information from a FRU. Returns a comma separated
				list of LEDS and the number of FRU supported user LEDs."
			::= { blade28FruEntry 4 }

		

		b28FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade28FruEntry 9 }
		
 		b28FRULabel OBJECT-TYPE
			SYNTAX DisplayString
			MAX-ACCESS read-only
			STATUS current
			DESCRIPTION
				"Get fru label of blade1."
			::= { blade28FruEntry 10 }
		
 		b28ResetReason OBJECT-TYPE
			SYNTAX DisplayString
			MAX-ACCESS read-only
			STATUS current
			DESCRIPTION
				"Delete fru label of smm."
			::= { blade28FruEntry 11 }
		
 		blade28FruLedTable OBJECT-TYPE
			SYNTAX SEQUENCE OF Blade28FruLedEntry
			MAX-ACCESS not-accessible
			STATUS current
			DESCRIPTION
				"A table containing the list of led information."
			::= { blade28 2003 }
		
 		blade28FruLedEntry OBJECT-TYPE
			SYNTAX Blade28FruLedEntry
			MAX-ACCESS not-accessible
			STATUS current
			DESCRIPTION
				"Information about a particular current led."
			INDEX { b1FruID, b1FruLed }
			::= { blade28FruLedTable 1 }
		
		Blade28FruLedEntry ::=
			SEQUENCE { 
				b28FruID
					INTEGER,
				b28FruLed
					DisplayString,
				b28FruLedColorProps
					DisplayString,
				b28FruLedState
					DisplayString
			 }

 		b28FruID OBJECT-TYPE
			SYNTAX INTEGER
			MAX-ACCESS not-accessible
			STATUS current
			DESCRIPTION
				" "
			::= { blade28FruLedEntry 1 }
		
 		b28FruLed OBJECT-TYPE
			SYNTAX DisplayString
			MAX-ACCESS not-accessible
			STATUS current
			DESCRIPTION
				" "
			::= { blade28FruLedEntry 2 }
		
 		b28FruLedColorProps OBJECT-TYPE
			SYNTAX DisplayString
			MAX-ACCESS read-only
			STATUS current
			DESCRIPTION
				"Finds out what colors are supported by the LED"
			::= { blade28FruLedEntry 3 }
		
 		b28FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade28FruLedEntry 4 }
		
 		blade28FruDescriptionTable OBJECT-TYPE
			SYNTAX SEQUENCE OF Blade28FruDescriptionEntry
			MAX-ACCESS not-accessible
			STATUS current
			DESCRIPTION
				"A table containing the list of Blade1 FRU information."
			::= { blade28 2004 }
		
 		blade28FruDescriptionEntry OBJECT-TYPE
			SYNTAX Blade28FruDescriptionEntry
			MAX-ACCESS not-accessible
			STATUS current
			DESCRIPTION
				"Information about a particular current FRU."
			INDEX { b1fruNum }
			::= { blade28FruDescriptionTable 1 }
		
		Blade28FruDescriptionEntry ::=
			SEQUENCE { 
				b28fruNum
					INTEGER,
				b28fruBoardDescription
					DisplayString,
				b28fruBoardManufacturer
					DisplayString,
				b28fruBoardPartNumber
					DisplayString,
				b28fruBoardSerialNumber
					DisplayString,
				b28fruBoardManufactureDate
					DisplayString,
				b28fruProductDescription
					DisplayString,
				b28fruProductManufacturer
					DisplayString,
				b28fruProductPartNumber
					DisplayString,
				b28fruProductSerialNumber
					DisplayString,
				b28fruProductRevision
					DisplayString,
				b28fruAll
					DisplayString
			 }

 		b28fruNum OBJECT-TYPE
			SYNTAX INTEGER
			MAX-ACCESS not-accessible
			STATUS current
			DESCRIPTION
				"blade1 FRU's INDEX"
			::= { blade28FruDescriptionEntry 1 }
		
 		b28fruBoardDescription OBJECT-TYPE
			SYNTAX DisplayString
			MAX-ACCESS read-only
			STATUS current
			DESCRIPTION
				"Used to read the Board Description from the blade1 fru."
			::= { blade28FruDescriptionEntry 2 }
		
 		b28fruBoardManufacturer OBJECT-TYPE
			SYNTAX DisplayString
			MAX-ACCESS read-only
			STATUS current
			DESCRIPTION
				"Used to read the Board Manufacturer from the blade1 fru."
			::= { blade28FruDescriptionEntry 3 }
		
 		b28fruBoardPartNumber OBJECT-TYPE
			SYNTAX DisplayString
			MAX-ACCESS read-only
			STATUS current
			DESCRIPTION
				"Used to read the Board Part Number from the blade1 fru."
			::= { blade28FruDescriptionEntry 4 }
		
 		b28fruBoardSerialNumber OBJECT-TYPE
			SYNTAX DisplayString
			MAX-ACCESS read-only
			STATUS current
			DESCRIPTION
				"Used to read the Board Serial Number from the blade1 fru."
			::= { blade28FruDescriptionEntry 5 }
		
 		b28fruBoardManufactureDate OBJECT-TYPE
			SYNTAX DisplayString
			MAX-ACCESS read-only
			STATUS current
			DESCRIPTION
				"Used to read the Board Manufacture Date from the blade1 fru."
			::= { blade28FruDescriptionEntry 6 }
		
 		b28fruProductDescription OBJECT-TYPE
			SYNTAX DisplayString
			MAX-ACCESS read-only
			STATUS current
			DESCRIPTION
				"Used to read the Product Description from the blade1 fru."
			::= { blade28FruDescriptionEntry 7 }
		
 		b28fruProductManufacturer OBJECT-TYPE
			SYNTAX DisplayString
			MAX-ACCESS read-only
			STATUS current
			DESCRIPTION
				"Used to read the Product Manufacturer from the blade1 fru."
			::= { blade28FruDescriptionEntry 8 }
		
 		b28fruProductPartNumber OBJECT-TYPE
			SYNTAX DisplayString
			MAX-ACCESS read-only
			STATUS current
			DESCRIPTION
				"Used to read the Product Part Number from the blade1 fru."
			::= { blade28FruDescriptionEntry 9 }
		
 		b28fruProductSerialNumber OBJECT-TYPE
			SYNTAX DisplayString
			MAX-ACCESS read-only
			STATUS current
			DESCRIPTION
				"Used to read the Product Serial Number from the blade1 fru."
			::= { blade28FruDescriptionEntry 10 }
		
 		b28fruProductRevision OBJECT-TYPE
			SYNTAX DisplayString
			MAX-ACCESS read-only
			STATUS current
			DESCRIPTION
				"Used to read the Product Revision from the blade1 fru."
			::= { blade28FruDescriptionEntry 13 }
		
 		b28fruAll OBJECT-TYPE
			SYNTAX DisplayString
			MAX-ACCESS read-only
			STATUS current
			DESCRIPTION
				"Used to read the fru info all."
			::= { blade28FruDescriptionEntry 14 }
		
		blade28CPUTable OBJECT-TYPE
			SYNTAX SEQUENCE OF Blade28CPUEntry
			MAX-ACCESS not-accessible
			STATUS current
			DESCRIPTION
				"A table containing the list of Blade1 FRU information."
			::= { blade28 2006 }
		
		blade28CPUEntry OBJECT-TYPE
			SYNTAX Blade28CPUEntry
			MAX-ACCESS not-accessible
			STATUS current
			DESCRIPTION
				"Information about a particular current FRU."
			INDEX { b28CPUIndex }
			::= { blade28CPUTable 1 }
		
		Blade28CPUEntry ::=
			SEQUENCE { 
				b28CPUIndex
					INTEGER,
				b28CPUMark
					DisplayString,
				b28CPUInfo
					DisplayString,
				b28CPUPresent
					INTEGER,
				b28CPUHealth
					INTEGER,
				b28CPULocation
					DisplayString
			 }

		b28CPUIndex OBJECT-TYPE
			SYNTAX INTEGER
			MAX-ACCESS not-accessible
			STATUS current
			DESCRIPTION
				"CPU INDEX"
			::= { blade28CPUEntry 1 }
		
		b28CPUMark OBJECT-TYPE
			SYNTAX DisplayString
			MAX-ACCESS read-only
			STATUS current
			DESCRIPTION
				"Get the CPU silk-screen."
			::= { blade28CPUEntry 2 }
		
		b28CPUInfo OBJECT-TYPE
			SYNTAX DisplayString
			MAX-ACCESS read-only
			STATUS current
			DESCRIPTION
				"Get the CPU description of vendor, type and frequency."
			::= { blade28CPUEntry 3 }
		
		b28CPUPresent OBJECT-TYPE
			SYNTAX INTEGER
			MAX-ACCESS read-only
			STATUS current
			DESCRIPTION
				"Get the CPU presence status."
			::= { blade28CPUEntry 4 }
		
		b28CPUHealth OBJECT-TYPE
			SYNTAX INTEGER
			MAX-ACCESS read-only
			STATUS current
			DESCRIPTION
				"Get the CPU health status."
			::= { blade28CPUEntry 5 }
		
		b28CPULocation OBJECT-TYPE
			SYNTAX DisplayString
			MAX-ACCESS read-only
			STATUS current
			DESCRIPTION
				"Get the CPU location."
			::= { blade28CPUEntry 6 }
		
		blade28MemoryTable OBJECT-TYPE
			SYNTAX SEQUENCE OF Blade28MemoryEntry
			MAX-ACCESS not-accessible
			STATUS current
			DESCRIPTION
				"A table containing the list of Blade1 FRU information."
			::= { blade28 2007 }
		
		blade28MemoryEntry OBJECT-TYPE
			SYNTAX Blade28MemoryEntry
			MAX-ACCESS not-accessible
			STATUS current
			DESCRIPTION
				"Information about a particular current FRU."
			INDEX { b28MEMIndex }
			::= { blade28MemoryTable 1 }
		
		Blade28MemoryEntry ::=
			SEQUENCE { 
				b28MEMIndex
					INTEGER,
				b28MEMMark
					DisplayString,
				b28MEMInfo
					DisplayString,
				b28MEMPresent
					INTEGER,
				b28MEMHealth
					INTEGER,
				b28MEMLocation
					DisplayString
			 }

		b28MEMIndex OBJECT-TYPE
			SYNTAX INTEGER
			MAX-ACCESS not-accessible
			STATUS current
			DESCRIPTION
				"MEMORY INDEX"
			::= { blade28MemoryEntry 1 }
		
		b28MEMMark OBJECT-TYPE
			SYNTAX DisplayString
			MAX-ACCESS read-only
			STATUS current
			DESCRIPTION
				"Get the memory silk-screen."
			::= { blade28MemoryEntry 2 }
		
		b28MEMInfo OBJECT-TYPE
			SYNTAX DisplayString
			MAX-ACCESS read-only
			STATUS current
			DESCRIPTION
				"Get the memory description of vendor, frequency and capacity."
			::= { blade28MemoryEntry 3 }
		
		b28MEMPresent OBJECT-TYPE
			SYNTAX INTEGER
			MAX-ACCESS read-only
			STATUS current
			DESCRIPTION
				"Get the memory presence status."
			::= { blade28MemoryEntry 4 }
		
		b28MEMHealth OBJECT-TYPE
			SYNTAX INTEGER
			MAX-ACCESS read-only
			STATUS current
			DESCRIPTION
				"Get the memory health status."
			::= { blade28MemoryEntry 5 }
		
		b28MEMLocation OBJECT-TYPE
			SYNTAX DisplayString
			MAX-ACCESS read-only
			STATUS current
			DESCRIPTION
				"Get the memory location."
			::= { blade28MemoryEntry 6 }
		
		blade28MezzTable OBJECT-TYPE
			SYNTAX SEQUENCE OF Blade28MezzEntry
			MAX-ACCESS not-accessible
			STATUS current
			DESCRIPTION
				"A table containing the list of Blade1 FRU information."
			::= { blade28 2008 }
		
		blade28MezzEntry OBJECT-TYPE
			SYNTAX Blade28MezzEntry
			MAX-ACCESS not-accessible
			STATUS current
			DESCRIPTION
				"Information about a particular current FRU."
			INDEX { b28MezzIndex }
			::= { blade28MezzTable 1 }
		
		Blade28MezzEntry ::=
			SEQUENCE { 
				b28MezzIndex
					INTEGER,
				b28MezzMark
					DisplayString,
				b28MezzInfo
					DisplayString,
				b28MezzPresent
					INTEGER,
				b28MezzHealth
					INTEGER,
				b28MezzLocation
					DisplayString,
				b28MezzMac
					DisplayString
			 }

		b28MezzIndex OBJECT-TYPE
			SYNTAX INTEGER
			MAX-ACCESS not-accessible
			STATUS current
			DESCRIPTION
				"MEZZ INDEX"
			::= { blade28MezzEntry 1 }
		
		b28MezzMark OBJECT-TYPE
			SYNTAX DisplayString
			MAX-ACCESS read-only
			STATUS current
			DESCRIPTION
				"Get the MEZZ silk-screen."
			::= { blade28MezzEntry 2 }
		
		b28MezzInfo OBJECT-TYPE
			SYNTAX DisplayString
			MAX-ACCESS read-only
			STATUS current
			DESCRIPTION
				"Get the MEZZ description of type."
			::= { blade28MezzEntry 3 }
		
		b28MezzPresent OBJECT-TYPE
			SYNTAX INTEGER
			MAX-ACCESS read-only
			STATUS current
			DESCRIPTION
				"Get the MEZZ presence status."
			::= { blade28MezzEntry 4 }
		
		b28MezzHealth OBJECT-TYPE
			SYNTAX INTEGER
			MAX-ACCESS read-only
			STATUS current
			DESCRIPTION
				"Get the MEZZ health status."
			::= { blade28MezzEntry 5 }
		
		b28MezzLocation OBJECT-TYPE
			SYNTAX DisplayString
			MAX-ACCESS read-only
			STATUS current
			DESCRIPTION
				"Get the MEZZ location."
			::= { blade28MezzEntry 6 }
		
		b28MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade28MezzEntry 7 }
		
		blade28DiskTable OBJECT-TYPE
			SYNTAX SEQUENCE OF Blade28DiskEntry
			MAX-ACCESS not-accessible
			STATUS current
			DESCRIPTION
				"A table containing the list of Blade1 FRU information."
			::= { blade28 2009 }
		
		blade28DiskEntry OBJECT-TYPE
			SYNTAX Blade28DiskEntry
			MAX-ACCESS not-accessible
			STATUS current
			DESCRIPTION
				"Information about a particular current FRU."
			INDEX { b28DiskIndex }
			::= { blade28DiskTable 1 }
		
		Blade28DiskEntry ::=
			SEQUENCE { 
				b28DiskIndex
					INTEGER,
				b28DiskMark
					DisplayString,
				b28DiskInfo
					DisplayString,
				b28DiskPresent
					INTEGER,
				b28DiskHealth
					INTEGER,
				b28DiskLocation
					DisplayString
			 }

		b28DiskIndex OBJECT-TYPE
			SYNTAX INTEGER
			MAX-ACCESS not-accessible
			STATUS current
			DESCRIPTION
				"DISK INDEX"
			::= { blade28DiskEntry 1 }
		
		b28DiskMark OBJECT-TYPE
			SYNTAX DisplayString
			MAX-ACCESS read-only
			STATUS current
			DESCRIPTION
				"Get the disk silk-screen."
			::= { blade28DiskEntry 2 }
		
		b28DiskInfo OBJECT-TYPE
			SYNTAX DisplayString
			MAX-ACCESS read-only
			STATUS current
			DESCRIPTION
				"Get the disk description of vendor, capacity and speed."
			::= { blade28DiskEntry 3 }
		
		b28DiskPresent OBJECT-TYPE
			SYNTAX INTEGER
			MAX-ACCESS read-only
			STATUS current
			DESCRIPTION
				"Get the disk presence status."
			::= { blade28DiskEntry 4 }
		
		b28DiskHealth OBJECT-TYPE
			SYNTAX INTEGER
			MAX-ACCESS read-only
			STATUS current
			DESCRIPTION
				"Get the disk health status."
			::= { blade28DiskEntry 5 }
		
		b28DiskLocation OBJECT-TYPE
			SYNTAX DisplayString
			MAX-ACCESS read-only
			STATUS current
			DESCRIPTION
				"Get the disk location."
			::= { blade28DiskEntry 6 }
		
		blade28SecretKvmVmmTable OBJECT-TYPE
			SYNTAX SEQUENCE OF Blade28SecretKvmVmmEntry
			MAX-ACCESS not-accessible
			STATUS current
			DESCRIPTION
				"A table containing the list of Blade28 KVM&VMM secret information."
			::= { blade28 2010 }

		blade28SecretKvmVmmEntry OBJECT-TYPE
			SYNTAX Blade28SecretKvmVmmEntry
			MAX-ACCESS not-accessible
			STATUS current
			DESCRIPTION
				"Information about a particular current KVM&VMM."
			INDEX { b28SecretKvmVmmIndex }
			::= { blade28SecretKvmVmmTable 1 }
		Blade28SecretKvmVmmEntry ::=
			SEQUENCE { 
				b28SecretKvmVmmIndex
					INTEGER,
				b28SecretKvmState
					INTEGER,
				b28SecretVmmState
					INTEGER,
				b28MMSecretVmmKey
					DisplayString,
				b28SecretVmmKey
					DisplayString
			 }
		b28SecretKvmVmmIndex OBJECT-TYPE
			SYNTAX INTEGER
			MAX-ACCESS not-accessible
			STATUS current
			DESCRIPTION
				"KVM&VMM INDEX."
			::= { blade28SecretKvmVmmEntry 1 }
		b28SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade28SecretKvmVmmEntry 2 }
		b28SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade28SecretKvmVmmEntry 3 }
		b28MMSecretVmmKey OBJECT-TYPE
			SYNTAX DisplayString
			MAX-ACCESS read-only
			STATUS current
			DESCRIPTION
				"Get the MM secret VMM key."
			::= { blade28SecretKvmVmmEntry 4 }
		b28SecretVmmKey OBJECT-TYPE
			SYNTAX DisplayString
			MAX-ACCESS read-write
			STATUS current
			DESCRIPTION
				"Set the secret VMM key."
			::= { blade28SecretKvmVmmEntry 5 }
		blade29 OBJECT IDENTIFIER ::= { blades 29 }

		
 		b29DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade29 4 }
		
 		b29PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade29 5 }
		
 		b29Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade29 6 }

		
 		b29Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade29 8 }
		
 		b29HealthEvents OBJECT-TYPE
			SYNTAX DisplayString
			MAX-ACCESS read-only
			STATUS current
			DESCRIPTION
				"Events that contribute to the b1Health of the b1Location.  
				This is a list of events currently happening on the 
				b1Location."
			::= { blade29 9 }
		
 		b29ClearSEL OBJECT-TYPE
			SYNTAX INTEGER { clear(1) }
			MAX-ACCESS read-write
			STATUS current
			DESCRIPTION
				"Clean the BMC's SEL on the board."
			::= { blade29 12 }
		
 		b29ExDiskBoardPresence OBJECT-TYPE
			SYNTAX INTEGER
				{
				not-present(0),
				present(1)
				}
			MAX-ACCESS read-only
			STATUS current
			DESCRIPTION
				"Used to find out if the extended disk board is present.
				0 - not present
				1 - present"
			::= { blade29 14 }
		
 		b29BladeVersion OBJECT-TYPE
			SYNTAX DisplayString
			MAX-ACCESS read-only
			STATUS current
			DESCRIPTION
				"display the Version of board1."
			::= { blade29 20 }
		
 		b29MACAddress OBJECT-TYPE
			SYNTAX DisplayString
			MAX-ACCESS read-only
			STATUS current
			DESCRIPTION
				"display the MACAddress of board1."
			::= { blade29 21 }
		
				
							
		
 		b29Safepwofftime OBJECT-TYPE
			SYNTAX INTEGER
			MAX-ACCESS read-write
			STATUS current
			DESCRIPTION
				"the safe poweroff time.
				"
			::= { blade29 26 }
		
 		b29BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]      
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]                     
				6=Force boot into BIOS Setup
				15=Force boot from Floppy/primary removable media           
				
				"
			::= { blade29 32 }
		
 		b29Systeminfo OBJECT-TYPE
			SYNTAX DisplayString
			MAX-ACCESS read-write
			STATUS current
			DESCRIPTION
				"display the system information of board1."
			::= { blade29 36 }

		
 		b29SystemProperties OBJECT-TYPE
			SYNTAX DisplayString
			MAX-ACCESS read-only
			STATUS current
			DESCRIPTION
				"Get the power of blade1."
			::= { blade29 39 }
		
 		b29BiosCfg OBJECT-TYPE
			SYNTAX DisplayString
			MAX-ACCESS read-write
			STATUS current
			DESCRIPTION
				"Get the power of blade1."
			::= { blade29 40 }
		
 		b29WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade29 41 }
		
 		b29RealTimePower OBJECT-TYPE
			SYNTAX INTEGER
			MAX-ACCESS read-only
			STATUS current
			DESCRIPTION
				" "
			::= { blade29 43 }
		
 		b29PowerCapping OBJECT-TYPE
			SYNTAX DisplayString
			MAX-ACCESS read-write
			STATUS current
			DESCRIPTION
				" "
			::= { blade29 44 }
		
 		b29Powerreference OBJECT-TYPE
			SYNTAX INTEGER
			MAX-ACCESS read-only
			STATUS current
			DESCRIPTION
				" "
			::= { blade29 45 }
		
 		b29ClearBiosConfig OBJECT-TYPE
			SYNTAX INTEGER
			MAX-ACCESS read-write
			STATUS current
			DESCRIPTION
				" "
			::= { blade29 46 }
		
 		b29BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade29 47 }
		
 		b29BmcUserAdd OBJECT-TYPE
			SYNTAX DisplayString
			MAX-ACCESS read-write
			STATUS current
			DESCRIPTION
				"Used to Add the BMC User
				settable format:
				username,passwd"
			::= { blade29 48 }
		
 		b29BmcUserDel OBJECT-TYPE
			SYNTAX DisplayString
			MAX-ACCESS read-write
			STATUS current
			DESCRIPTION
				"Used to Del the BMC User
				settable format:
				username"
			::= { blade29 49 }
		
 		b29BmcUserPasswd OBJECT-TYPE
			SYNTAX DisplayString
			MAX-ACCESS read-write
			STATUS current
			DESCRIPTION
				"Used to Change the BMC User Passwd
				settable format:
				username,passwd"
			::= { blade29 50 }
		
 		b29BmcUserpropertychg OBJECT-TYPE
			SYNTAX DisplayString
			MAX-ACCESS read-write
			STATUS current
			DESCRIPTION
				"Used to Change the BMC User Property
				settable format:
				username,property"
			::= { blade29 51 }
		
 		b29BmcGateway OBJECT-TYPE
			SYNTAX DisplayString
			MAX-ACCESS read-write
			STATUS current
			DESCRIPTION
				"Read or set the gateway."
			::= { blade29 52 }
		
 		b29SlotBitmap OBJECT-TYPE
			SYNTAX INTEGER
			MAX-ACCESS read-only
			STATUS current
			DESCRIPTION
				" "
			::= { blade29 55 }
		
		b29systemGuid OBJECT-TYPE
			SYNTAX DisplayString
			MAX-ACCESS read-only
			STATUS current
			DESCRIPTION
				" "
			::= { blade29 56 }
		
		b29ProductName OBJECT-TYPE
			SYNTAX DisplayString
			MAX-ACCESS read-only
			STATUS current
			DESCRIPTION
				"display the Version of board1."
			::= { blade29 57 }
			
		b29BundleVersion OBJECT-TYPE
			SYNTAX DisplayString
			MAX-ACCESS read-write
			STATUS current
			DESCRIPTION
				"Get or set the board29 bundle version."
			::= { blade29 58 }

 		blade29SensorTargetTable OBJECT-TYPE
			SYNTAX SEQUENCE OF Blade29SensorTargetEntry
			MAX-ACCESS not-accessible
			STATUS current
			DESCRIPTION
				"A table containing the list of sensor information."
			::= { blade29 2001 }
		
 		blade29SensorTargetEntry OBJECT-TYPE
			SYNTAX Blade29SensorTargetEntry
			MAX-ACCESS not-accessible
			STATUS current
			DESCRIPTION
				"Information about a particular current sensor."
			INDEX { b1Target }
			::= { blade29SensorTargetTable 1 }
		
		Blade29SensorTargetEntry ::=
			SEQUENCE { 
				b29Target
					DisplayString,
				b29Current
					DisplayString,
				b29ThresholdsAll
					DisplayString,
				b29UpperCritical
					DisplayString,
				b29UpperNonCritical
					DisplayString,
				b29UpperNonRecoverable
					DisplayString,
				b29LowerNonCritical
					DisplayString,
				b29LowerCritical
					DisplayString,
				b29LowerNonRecoverable
					DisplayString,
				b29SensorHealth
					INTEGER,
				b29SensorHealthEvents
					DisplayString,
				b29NegativeHysteresis
					DisplayString,
				b29PositiveHysteresis
					DisplayString,
				b29SensorType
					DisplayString,
				b29SensorFRUInfo
					DisplayString
			 }

 		b29Target OBJECT-TYPE
			SYNTAX DisplayString
			MAX-ACCESS not-accessible
			STATUS current
			DESCRIPTION
				"sensor Name"
			::= { blade29SensorTargetEntry 1 }
		
 		b29Current OBJECT-TYPE
			SYNTAX DisplayString
			MAX-ACCESS read-only
			STATUS current
			DESCRIPTION
				"Display the current value of a sensor."
			::= { blade29SensorTargetEntry 2 }
		
 		b29ThresholdsAll OBJECT-TYPE
			SYNTAX DisplayString
			MAX-ACCESS read-only
			STATUS current
			DESCRIPTION
				"All thresholds of a sensor"
			::= { blade29SensorTargetEntry 3 }
		
 		b29UpperCritical OBJECT-TYPE
			SYNTAX DisplayString
			MAX-ACCESS read-write
			STATUS current
			DESCRIPTION
				"Upper critical thresholds"
			::= { blade29SensorTargetEntry 4 }
		
 		b29UpperNonCritical OBJECT-TYPE
			SYNTAX DisplayString
			MAX-ACCESS read-write
			STATUS current
			DESCRIPTION
				"Upper non-critical thresholds"
			::= { blade29SensorTargetEntry 5 }
		
 		b29UpperNonRecoverable OBJECT-TYPE
			SYNTAX DisplayString
			MAX-ACCESS read-write
			STATUS current
			DESCRIPTION
				"Upper non-recoverable thresholds"
			::= { blade29SensorTargetEntry 6 }
		
 		b29LowerNonCritical OBJECT-TYPE
			SYNTAX DisplayString
			MAX-ACCESS read-write
			STATUS current
			DESCRIPTION
				"Lower non-critical thresholds"
			::= { blade29SensorTargetEntry 7 }
		
 		b29LowerCritical OBJECT-TYPE
			SYNTAX DisplayString
			MAX-ACCESS read-write
			STATUS current
			DESCRIPTION
				"Lower critical thresholds"
			::= { blade29SensorTargetEntry 8 }
		
 		b29LowerNonRecoverable OBJECT-TYPE
			SYNTAX DisplayString
			MAX-ACCESS read-write
			STATUS current
			DESCRIPTION
				"Lower non-recoverable thresholds"
			::= { blade29SensorTargetEntry 9 }
		
 		b29SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade29SensorTargetEntry 10 }
		
 		b29SensorHealthEvents OBJECT-TYPE
			SYNTAX DisplayString
			MAX-ACCESS read-only
			STATUS current
			DESCRIPTION
				"Events that contribute to the b1Health of the b1Location.  
				This is a list of events currently happening on the 
				b1Location."
			::= { blade29SensorTargetEntry 11 }
		
		
 		b29NegativeHysteresis OBJECT-TYPE
			SYNTAX DisplayString
			MAX-ACCESS read-write
			STATUS current
			DESCRIPTION
				"Get/Set the negativeHysteresis value."
			::= { blade29SensorTargetEntry 16 }
		
 		b29PositiveHysteresis OBJECT-TYPE
			SYNTAX DisplayString
			MAX-ACCESS read-write
			STATUS current
			DESCRIPTION
				"Get/Set the positiveHysteresis value."
			::= { blade29SensorTargetEntry 17 }
		
 		b29SensorType OBJECT-TYPE
			SYNTAX DisplayString
			MAX-ACCESS read-only
			STATUS current
			DESCRIPTION
				"Get the type of the sensor."
			::= { blade29SensorTargetEntry 18 }
		
 		b29SensorFRUInfo OBJECT-TYPE
			SYNTAX DisplayString
			MAX-ACCESS read-only
			STATUS current
			DESCRIPTION
				"Get the fruinfo of the sensor."
			::= { blade29SensorTargetEntry 19 }
		
 		blade29FruTable OBJECT-TYPE
			SYNTAX SEQUENCE OF Blade29FruEntry
			MAX-ACCESS not-accessible
			STATUS current
			DESCRIPTION
				"A table containing the list of FRU information."
			::= { blade29 2002 }
		
 		blade29FruEntry OBJECT-TYPE
			SYNTAX Blade29FruEntry
			MAX-ACCESS not-accessible
			STATUS current
			DESCRIPTION
				"Information about a particular current FRU."
			INDEX { b1fruNumber }
			::= { blade29FruTable 1 }
		
		Blade29FruEntry ::=
			SEQUENCE { 
				b29fruNumber
					INTEGER,
				b29FruHotSwapState
					DisplayString,
				b29FruLedProperties
					DisplayString,
				b29FRUControl
					INTEGER,
				b29FRULabel
					DisplayString,
				b29ResetReason
					DisplayString
			 }

 		b29fruNumber OBJECT-TYPE
			SYNTAX INTEGER
			MAX-ACCESS not-accessible
			STATUS current
			DESCRIPTION
				" "
			::= { blade29FruEntry 1 }
		
 		b29FruHotSwapState OBJECT-TYPE
			SYNTAX DisplayString
			MAX-ACCESS read-only
			STATUS current
			DESCRIPTION
				"Retrieve the hot swap state of the FRU from the 
				internally known hot swap states of blade1."
			::= { blade29FruEntry 3 }
		
 		b29FruLedProperties OBJECT-TYPE
			SYNTAX DisplayString
			MAX-ACCESS read-only
			STATUS current
			DESCRIPTION
				"Retrieves the LED support information from a FRU. Returns a comma separated
				list of LEDS and the number of FRU supported user LEDs."
			::= { blade29FruEntry 4 }

		

		b29FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade29FruEntry 9 }
		
 		b29FRULabel OBJECT-TYPE
			SYNTAX DisplayString
			MAX-ACCESS read-only
			STATUS current
			DESCRIPTION
				"Get fru label of blade1."
			::= { blade29FruEntry 10 }
		
 		b29ResetReason OBJECT-TYPE
			SYNTAX DisplayString
			MAX-ACCESS read-only
			STATUS current
			DESCRIPTION
				"Delete fru label of smm."
			::= { blade29FruEntry 11 }
		
 		blade29FruLedTable OBJECT-TYPE
			SYNTAX SEQUENCE OF Blade29FruLedEntry
			MAX-ACCESS not-accessible
			STATUS current
			DESCRIPTION
				"A table containing the list of led information."
			::= { blade29 2003 }
		
 		blade29FruLedEntry OBJECT-TYPE
			SYNTAX Blade29FruLedEntry
			MAX-ACCESS not-accessible
			STATUS current
			DESCRIPTION
				"Information about a particular current led."
			INDEX { b1FruID, b1FruLed }
			::= { blade29FruLedTable 1 }
		
		Blade29FruLedEntry ::=
			SEQUENCE { 
				b29FruID
					INTEGER,
				b29FruLed
					DisplayString,
				b29FruLedColorProps
					DisplayString,
				b29FruLedState
					DisplayString
			 }

 		b29FruID OBJECT-TYPE
			SYNTAX INTEGER
			MAX-ACCESS not-accessible
			STATUS current
			DESCRIPTION
				" "
			::= { blade29FruLedEntry 1 }
		
 		b29FruLed OBJECT-TYPE
			SYNTAX DisplayString
			MAX-ACCESS not-accessible
			STATUS current
			DESCRIPTION
				" "
			::= { blade29FruLedEntry 2 }
		
 		b29FruLedColorProps OBJECT-TYPE
			SYNTAX DisplayString
			MAX-ACCESS read-only
			STATUS current
			DESCRIPTION
				"Finds out what colors are supported by the LED"
			::= { blade29FruLedEntry 3 }
		
 		b29FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade29FruLedEntry 4 }
		
 		blade29FruDescriptionTable OBJECT-TYPE
			SYNTAX SEQUENCE OF Blade29FruDescriptionEntry
			MAX-ACCESS not-accessible
			STATUS current
			DESCRIPTION
				"A table containing the list of Blade1 FRU information."
			::= { blade29 2004 }
		
 		blade29FruDescriptionEntry OBJECT-TYPE
			SYNTAX Blade29FruDescriptionEntry
			MAX-ACCESS not-accessible
			STATUS current
			DESCRIPTION
				"Information about a particular current FRU."
			INDEX { b1fruNum }
			::= { blade29FruDescriptionTable 1 }
		
		Blade29FruDescriptionEntry ::=
			SEQUENCE { 
				b29fruNum
					INTEGER,
				b29fruBoardDescription
					DisplayString,
				b29fruBoardManufacturer
					DisplayString,
				b29fruBoardPartNumber
					DisplayString,
				b29fruBoardSerialNumber
					DisplayString,
				b29fruBoardManufactureDate
					DisplayString,
				b29fruProductDescription
					DisplayString,
				b29fruProductManufacturer
					DisplayString,
				b29fruProductPartNumber
					DisplayString,
				b29fruProductSerialNumber
					DisplayString,
				b29fruProductRevision
					DisplayString,
				b29fruAll
					DisplayString
			 }

 		b29fruNum OBJECT-TYPE
			SYNTAX INTEGER
			MAX-ACCESS not-accessible
			STATUS current
			DESCRIPTION
				"blade1 FRU's INDEX"
			::= { blade29FruDescriptionEntry 1 }
		
 		b29fruBoardDescription OBJECT-TYPE
			SYNTAX DisplayString
			MAX-ACCESS read-only
			STATUS current
			DESCRIPTION
				"Used to read the Board Description from the blade1 fru."
			::= { blade29FruDescriptionEntry 2 }
		
 		b29fruBoardManufacturer OBJECT-TYPE
			SYNTAX DisplayString
			MAX-ACCESS read-only
			STATUS current
			DESCRIPTION
				"Used to read the Board Manufacturer from the blade1 fru."
			::= { blade29FruDescriptionEntry 3 }
		
 		b29fruBoardPartNumber OBJECT-TYPE
			SYNTAX DisplayString
			MAX-ACCESS read-only
			STATUS current
			DESCRIPTION
				"Used to read the Board Part Number from the blade1 fru."
			::= { blade29FruDescriptionEntry 4 }
		
 		b29fruBoardSerialNumber OBJECT-TYPE
			SYNTAX DisplayString
			MAX-ACCESS read-only
			STATUS current
			DESCRIPTION
				"Used to read the Board Serial Number from the blade1 fru."
			::= { blade29FruDescriptionEntry 5 }
		
 		b29fruBoardManufactureDate OBJECT-TYPE
			SYNTAX DisplayString
			MAX-ACCESS read-only
			STATUS current
			DESCRIPTION
				"Used to read the Board Manufacture Date from the blade1 fru."
			::= { blade29FruDescriptionEntry 6 }
		
 		b29fruProductDescription OBJECT-TYPE
			SYNTAX DisplayString
			MAX-ACCESS read-only
			STATUS current
			DESCRIPTION
				"Used to read the Product Description from the blade1 fru."
			::= { blade29FruDescriptionEntry 7 }
		
 		b29fruProductManufacturer OBJECT-TYPE
			SYNTAX DisplayString
			MAX-ACCESS read-only
			STATUS current
			DESCRIPTION
				"Used to read the Product Manufacturer from the blade1 fru."
			::= { blade29FruDescriptionEntry 8 }
		
 		b29fruProductPartNumber OBJECT-TYPE
			SYNTAX DisplayString
			MAX-ACCESS read-only
			STATUS current
			DESCRIPTION
				"Used to read the Product Part Number from the blade1 fru."
			::= { blade29FruDescriptionEntry 9 }
		
 		b29fruProductSerialNumber OBJECT-TYPE
			SYNTAX DisplayString
			MAX-ACCESS read-only
			STATUS current
			DESCRIPTION
				"Used to read the Product Serial Number from the blade1 fru."
			::= { blade29FruDescriptionEntry 10 }
		
 		b29fruProductRevision OBJECT-TYPE
			SYNTAX DisplayString
			MAX-ACCESS read-only
			STATUS current
			DESCRIPTION
				"Used to read the Product Revision from the blade1 fru."
			::= { blade29FruDescriptionEntry 13 }
		
 		b29fruAll OBJECT-TYPE
			SYNTAX DisplayString
			MAX-ACCESS read-only
			STATUS current
			DESCRIPTION
				"Used to read the fru info all."
			::= { blade29FruDescriptionEntry 14 }
		
		blade29CPUTable OBJECT-TYPE
			SYNTAX SEQUENCE OF Blade29CPUEntry
			MAX-ACCESS not-accessible
			STATUS current
			DESCRIPTION
				"A table containing the list of Blade1 FRU information."
			::= { blade29 2006 }
		
		blade29CPUEntry OBJECT-TYPE
			SYNTAX Blade29CPUEntry
			MAX-ACCESS not-accessible
			STATUS current
			DESCRIPTION
				"Information about a particular current FRU."
			INDEX { b29CPUIndex }
			::= { blade29CPUTable 1 }
		
		Blade29CPUEntry ::=
			SEQUENCE { 
				b29CPUIndex
					INTEGER,
				b29CPUMark
					DisplayString,
				b29CPUInfo
					DisplayString,
				b29CPUPresent
					INTEGER,
				b29CPUHealth
					INTEGER,
				b29CPULocation
					DisplayString
			 }

		b29CPUIndex OBJECT-TYPE
			SYNTAX INTEGER
			MAX-ACCESS not-accessible
			STATUS current
			DESCRIPTION
				"CPU INDEX"
			::= { blade29CPUEntry 1 }
		
		b29CPUMark OBJECT-TYPE
			SYNTAX DisplayString
			MAX-ACCESS read-only
			STATUS current
			DESCRIPTION
				"Get the CPU silk-screen."
			::= { blade29CPUEntry 2 }
		
		b29CPUInfo OBJECT-TYPE
			SYNTAX DisplayString
			MAX-ACCESS read-only
			STATUS current
			DESCRIPTION
				"Get the CPU description of vendor, type and frequency."
			::= { blade29CPUEntry 3 }
		
		b29CPUPresent OBJECT-TYPE
			SYNTAX INTEGER
			MAX-ACCESS read-only
			STATUS current
			DESCRIPTION
				"Get the CPU presence status."
			::= { blade29CPUEntry 4 }
		
		b29CPUHealth OBJECT-TYPE
			SYNTAX INTEGER
			MAX-ACCESS read-only
			STATUS current
			DESCRIPTION
				"Get the CPU health status."
			::= { blade29CPUEntry 5 }
		
		b29CPULocation OBJECT-TYPE
			SYNTAX DisplayString
			MAX-ACCESS read-only
			STATUS current
			DESCRIPTION
				"Get the CPU location."
			::= { blade29CPUEntry 6 }
		
		blade29MemoryTable OBJECT-TYPE
			SYNTAX SEQUENCE OF Blade29MemoryEntry
			MAX-ACCESS not-accessible
			STATUS current
			DESCRIPTION
				"A table containing the list of Blade1 FRU information."
			::= { blade29 2007 }
		
		blade29MemoryEntry OBJECT-TYPE
			SYNTAX Blade29MemoryEntry
			MAX-ACCESS not-accessible
			STATUS current
			DESCRIPTION
				"Information about a particular current FRU."
			INDEX { b29MEMIndex }
			::= { blade29MemoryTable 1 }
		
		Blade29MemoryEntry ::=
			SEQUENCE { 
				b29MEMIndex
					INTEGER,
				b29MEMMark
					DisplayString,
				b29MEMInfo
					DisplayString,
				b29MEMPresent
					INTEGER,
				b29MEMHealth
					INTEGER,
				b29MEMLocation
					DisplayString
			 }

		b29MEMIndex OBJECT-TYPE
			SYNTAX INTEGER
			MAX-ACCESS not-accessible
			STATUS current
			DESCRIPTION
				"MEMORY INDEX"
			::= { blade29MemoryEntry 1 }
		
		b29MEMMark OBJECT-TYPE
			SYNTAX DisplayString
			MAX-ACCESS read-only
			STATUS current
			DESCRIPTION
				"Get the memory silk-screen."
			::= { blade29MemoryEntry 2 }
		
		b29MEMInfo OBJECT-TYPE
			SYNTAX DisplayString
			MAX-ACCESS read-only
			STATUS current
			DESCRIPTION
				"Get the memory description of vendor, frequency and capacity."
			::= { blade29MemoryEntry 3 }
		
		b29MEMPresent OBJECT-TYPE
			SYNTAX INTEGER
			MAX-ACCESS read-only
			STATUS current
			DESCRIPTION
				"Get the memory presence status."
			::= { blade29MemoryEntry 4 }
		
		b29MEMHealth OBJECT-TYPE
			SYNTAX INTEGER
			MAX-ACCESS read-only
			STATUS current
			DESCRIPTION
				"Get the memory health status."
			::= { blade29MemoryEntry 5 }
		
		b29MEMLocation OBJECT-TYPE
			SYNTAX DisplayString
			MAX-ACCESS read-only
			STATUS current
			DESCRIPTION
				"Get the memory location."
			::= { blade29MemoryEntry 6 }
		
		blade29MezzTable OBJECT-TYPE
			SYNTAX SEQUENCE OF Blade29MezzEntry
			MAX-ACCESS not-accessible
			STATUS current
			DESCRIPTION
				"A table containing the list of Blade1 FRU information."
			::= { blade29 2008 }
		
		blade29MezzEntry OBJECT-TYPE
			SYNTAX Blade29MezzEntry
			MAX-ACCESS not-accessible
			STATUS current
			DESCRIPTION
				"Information about a particular current FRU."
			INDEX { b29MezzIndex }
			::= { blade29MezzTable 1 }
		
		Blade29MezzEntry ::=
			SEQUENCE { 
				b29MezzIndex
					INTEGER,
				b29MezzMark
					DisplayString,
				b29MezzInfo
					DisplayString,
				b29MezzPresent
					INTEGER,
				b29MezzHealth
					INTEGER,
				b29MezzLocation
					DisplayString,
				b29MezzMac
					DisplayString
			 }

		b29MezzIndex OBJECT-TYPE
			SYNTAX INTEGER
			MAX-ACCESS not-accessible
			STATUS current
			DESCRIPTION
				"MEZZ INDEX"
			::= { blade29MezzEntry 1 }
		
		b29MezzMark OBJECT-TYPE
			SYNTAX DisplayString
			MAX-ACCESS read-only
			STATUS current
			DESCRIPTION
				"Get the MEZZ silk-screen."
			::= { blade29MezzEntry 2 }
		
		b29MezzInfo OBJECT-TYPE
			SYNTAX DisplayString
			MAX-ACCESS read-only
			STATUS current
			DESCRIPTION
				"Get the MEZZ description of type."
			::= { blade29MezzEntry 3 }
		
		b29MezzPresent OBJECT-TYPE
			SYNTAX INTEGER
			MAX-ACCESS read-only
			STATUS current
			DESCRIPTION
				"Get the MEZZ presence status."
			::= { blade29MezzEntry 4 }
		
		b29MezzHealth OBJECT-TYPE
			SYNTAX INTEGER
			MAX-ACCESS read-only
			STATUS current
			DESCRIPTION
				"Get the MEZZ health status."
			::= { blade29MezzEntry 5 }
		
		b29MezzLocation OBJECT-TYPE
			SYNTAX DisplayString
			MAX-ACCESS read-only
			STATUS current
			DESCRIPTION
				"Get the MEZZ location."
			::= { blade29MezzEntry 6 }
		
		b29MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade29MezzEntry 7 }
		
		blade29DiskTable OBJECT-TYPE
			SYNTAX SEQUENCE OF Blade29DiskEntry
			MAX-ACCESS not-accessible
			STATUS current
			DESCRIPTION
				"A table containing the list of Blade1 FRU information."
			::= { blade29 2009 }
		
		blade29DiskEntry OBJECT-TYPE
			SYNTAX Blade29DiskEntry
			MAX-ACCESS not-accessible
			STATUS current
			DESCRIPTION
				"Information about a particular current FRU."
			INDEX { b29DiskIndex }
			::= { blade29DiskTable 1 }
		
		Blade29DiskEntry ::=
			SEQUENCE { 
				b29DiskIndex
					INTEGER,
				b29DiskMark
					DisplayString,
				b29DiskInfo
					DisplayString,
				b29DiskPresent
					INTEGER,
				b29DiskHealth
					INTEGER,
				b29DiskLocation
					DisplayString
			 }

		b29DiskIndex OBJECT-TYPE
			SYNTAX INTEGER
			MAX-ACCESS not-accessible
			STATUS current
			DESCRIPTION
				"DISK INDEX"
			::= { blade29DiskEntry 1 }
		
		b29DiskMark OBJECT-TYPE
			SYNTAX DisplayString
			MAX-ACCESS read-only
			STATUS current
			DESCRIPTION
				"Get the disk silk-screen."
			::= { blade29DiskEntry 2 }
		
		b29DiskInfo OBJECT-TYPE
			SYNTAX DisplayString
			MAX-ACCESS read-only
			STATUS current
			DESCRIPTION
				"Get the disk description of vendor, capacity and speed."
			::= { blade29DiskEntry 3 }
		
		b29DiskPresent OBJECT-TYPE
			SYNTAX INTEGER
			MAX-ACCESS read-only
			STATUS current
			DESCRIPTION
				"Get the disk presence status."
			::= { blade29DiskEntry 4 }
		
		b29DiskHealth OBJECT-TYPE
			SYNTAX INTEGER
			MAX-ACCESS read-only
			STATUS current
			DESCRIPTION
				"Get the disk health status."
			::= { blade29DiskEntry 5 }
		
		b29DiskLocation OBJECT-TYPE
			SYNTAX DisplayString
			MAX-ACCESS read-only
			STATUS current
			DESCRIPTION
				"Get the disk location."
			::= { blade29DiskEntry 6 }
		
		blade29SecretKvmVmmTable OBJECT-TYPE
			SYNTAX SEQUENCE OF Blade29SecretKvmVmmEntry
			MAX-ACCESS not-accessible
			STATUS current
			DESCRIPTION
				"A table containing the list of Blade29 KVM&VMM secret information."
			::= { blade29 2010 }

		blade29SecretKvmVmmEntry OBJECT-TYPE
			SYNTAX Blade29SecretKvmVmmEntry
			MAX-ACCESS not-accessible
			STATUS current
			DESCRIPTION
				"Information about a particular current KVM&VMM."
			INDEX { b29SecretKvmVmmIndex }
			::= { blade29SecretKvmVmmTable 1 }
		Blade29SecretKvmVmmEntry ::=
			SEQUENCE { 
				b29SecretKvmVmmIndex
					INTEGER,
				b29SecretKvmState
					INTEGER,
				b29SecretVmmState
					INTEGER,
				b29MMSecretVmmKey
					DisplayString,
				b29SecretVmmKey
					DisplayString
			 }
		b29SecretKvmVmmIndex OBJECT-TYPE
			SYNTAX INTEGER
			MAX-ACCESS not-accessible
			STATUS current
			DESCRIPTION
				"KVM&VMM INDEX."
			::= { blade29SecretKvmVmmEntry 1 }
		b29SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade29SecretKvmVmmEntry 2 }
		b29SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade29SecretKvmVmmEntry 3 }
		b29MMSecretVmmKey OBJECT-TYPE
			SYNTAX DisplayString
			MAX-ACCESS read-only
			STATUS current
			DESCRIPTION
				"Get the MM secret VMM key."
			::= { blade29SecretKvmVmmEntry 4 }
		b29SecretVmmKey OBJECT-TYPE
			SYNTAX DisplayString
			MAX-ACCESS read-write
			STATUS current
			DESCRIPTION
				"Set the secret VMM key."
			::= { blade29SecretKvmVmmEntry 5 }
		blade30 OBJECT IDENTIFIER ::= { blades 30 }

		
 		b30DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade30 4 }
		
 		b30PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade
				"
			::= { blade30 5 }
		
 		b30Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade30 6 }

		
 		b30Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b1Health information about a particular b1Location. 
				This will be one of the following:
				(0-ok, 1-minor, 2-major, 3-majorandminor,4-critical,5-criticalandminor,6-criticalandmajor,7-criticalandmajorandminor)"
			::= { blade30 8 }
		
 		b30HealthEvents OBJECT-TYPE
			SYNTAX DisplayString
			MAX-ACCESS read-only
			STATUS current
			DESCRIPTION
				"Events that contribute to the b1Health of the b1Location.  
				This is a list of events currently happening on the 
				b1Location."
			::= { blade30 9 }
		
 		b30ClearSEL OBJECT-TYPE
			SYNTAX INTEGER { clear(1) }
			MAX-ACCESS read-write
			STATUS current
			DESCRIPTION
				"Clean the BMC's SEL on the board."
			::= { blade30 12 }
		
 		b30ExDiskBoardPresence OBJECT-TYPE
			SYNTAX INTEGER
				{
				not-present(0),
				present(1)
				}
			MAX-ACCESS read-only
			STATUS current
			DESCRIPTION
				"Used to find out if the extended disk board is present.
				0 - not present
				1 - present"
			::= { blade30 14 }
		
 		b30BladeVersion OBJECT-TYPE
			SYNTAX DisplayString
			MAX-ACCESS read-only
			STATUS current
			DESCRIPTION
				"display the Version of board1."
			::= { blade30 20 }
		
 		b30MACAddress OBJECT-TYPE
			SYNTAX DisplayString
			MAX-ACCESS read-only
			STATUS current
			DESCRIPTION
				"display the MACAddress of board1."
			::= { blade30 21 }
		
				
							
		
 		b30Safepwofftime OBJECT-TYPE
			SYNTAX INTEGER
			MAX-ACCESS read-write
			STATUS current
			DESCRIPTION
				"the safe poweroff time.
				"
			::= { blade30 26 }
		
 		b30BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]
				6=Force boot into BIOS Setup
				15=Force boot from Floppy/primary removable media           
				
				"
			::= { blade30 32 }
		
 		b30Systeminfo OBJECT-TYPE
			SYNTAX DisplayString
			MAX-ACCESS read-write
			STATUS current
			DESCRIPTION
				"display the system information of board1."
			::= { blade30 36 }

		
 		b30SystemProperties OBJECT-TYPE
			SYNTAX DisplayString
			MAX-ACCESS read-only
			STATUS current
			DESCRIPTION
				"Get the power of blade1."
			::= { blade30 39 }
		
 		b30BiosCfg OBJECT-TYPE
			SYNTAX DisplayString
			MAX-ACCESS read-write
			STATUS current
			DESCRIPTION
				"Get the power of blade1."
			::= { blade30 40 }
		
 		b30WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade30 41 }
		
 		b30RealTimePower OBJECT-TYPE
			SYNTAX INTEGER
			MAX-ACCESS read-only
			STATUS current
			DESCRIPTION
				" "
			::= { blade30 43 }
		
 		b30PowerCapping OBJECT-TYPE
			SYNTAX DisplayString
			MAX-ACCESS read-write
			STATUS current
			DESCRIPTION
				" "
			::= { blade30 44 }
		
 		b30Powerreference OBJECT-TYPE
			SYNTAX INTEGER
			MAX-ACCESS read-only
			STATUS current
			DESCRIPTION
				" "
			::= { blade30 45 }
		
 		b30ClearBiosConfig OBJECT-TYPE
			SYNTAX INTEGER
			MAX-ACCESS read-write
			STATUS current
			DESCRIPTION
				" "
			::= { blade30 46 }
		
 		b30BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade30 47 }
		
 		b30BmcUserAdd OBJECT-TYPE
			SYNTAX DisplayString
			MAX-ACCESS read-write
			STATUS current
			DESCRIPTION
				"Used to Add the BMC User
				settable format:
				username,passwd"
			::= { blade30 48 }
		
 		b30BmcUserDel OBJECT-TYPE
			SYNTAX DisplayString
			MAX-ACCESS read-write
			STATUS current
			DESCRIPTION
				"Used to Del the BMC User
				settable format:
				username"
			::= { blade30 49 }
		
 		b30BmcUserPasswd OBJECT-TYPE
			SYNTAX DisplayString
			MAX-ACCESS read-write
			STATUS current
			DESCRIPTION
				"Used to Change the BMC User Passwd
				settable format:
				username,passwd"
			::= { blade30 50 }
		
 		b30BmcUserpropertychg OBJECT-TYPE
			SYNTAX DisplayString
			MAX-ACCESS read-write
			STATUS current
			DESCRIPTION
				"Used to Change the BMC User Property
				settable format:
				username,property"
			::= { blade30 51 }
		
 		b30BmcGateway OBJECT-TYPE
			SYNTAX DisplayString
			MAX-ACCESS read-write
			STATUS current
			DESCRIPTION
				"Read or set the gateway."
			::= { blade30 52 }
		
 		b30SlotBitmap OBJECT-TYPE
			SYNTAX INTEGER
			MAX-ACCESS read-only
			STATUS current
			DESCRIPTION
				" "
			::= { blade30 55 }
		
		b30systemGuid OBJECT-TYPE
			SYNTAX DisplayString
			MAX-ACCESS read-only
			STATUS current
			DESCRIPTION
				" "
			::= { blade30 56 }
		
		b30ProductName OBJECT-TYPE
			SYNTAX DisplayString
			MAX-ACCESS read-only
			STATUS current
			DESCRIPTION
				"display the Version of board1."
			::= { blade30 57 }
			
		b30BundleVersion OBJECT-TYPE
			SYNTAX DisplayString
			MAX-ACCESS read-write
			STATUS current
			DESCRIPTION
				"Get or set the board30 bundle version."
			::= { blade30 58 }

 		blade30SensorTargetTable OBJECT-TYPE
			SYNTAX SEQUENCE OF Blade30SensorTargetEntry
			MAX-ACCESS not-accessible
			STATUS current
			DESCRIPTION
				"A table containing the list of sensor information."
			::= { blade30 2001 }
		
 		blade30SensorTargetEntry OBJECT-TYPE
			SYNTAX Blade30SensorTargetEntry
			MAX-ACCESS not-accessible
			STATUS current
			DESCRIPTION
				"Information about a particular current sensor."
			INDEX { b1Target }
			::= { blade30SensorTargetTable 1 }
		
		Blade30SensorTargetEntry ::=
			SEQUENCE { 
				b30Target
					DisplayString,
				b30Current
					DisplayString,
				b30ThresholdsAll
					DisplayString,
				b30UpperCritical
					DisplayString,
				b30UpperNonCritical
					DisplayString,
				b30UpperNonRecoverable
					DisplayString,
				b30LowerNonCritical
					DisplayString,
				b30LowerCritical
					DisplayString,
				b30LowerNonRecoverable
					DisplayString,
				b30SensorHealth
					INTEGER,
				b30SensorHealthEvents
					DisplayString,
				b30NegativeHysteresis
					DisplayString,
				b30PositiveHysteresis
					DisplayString,
				b30SensorType
					DisplayString,
				b30SensorFRUInfo
					DisplayString
			 }

 		b30Target OBJECT-TYPE
			SYNTAX DisplayString
			MAX-ACCESS not-accessible
			STATUS current
			DESCRIPTION
				"sensor Name"
			::= { blade30SensorTargetEntry 1 }
		
 		b30Current OBJECT-TYPE
			SYNTAX DisplayString
			MAX-ACCESS read-only
			STATUS current
			DESCRIPTION
				"Display the current value of a sensor."
			::= { blade30SensorTargetEntry 2 }
		
 		b30ThresholdsAll OBJECT-TYPE
			SYNTAX DisplayString
			MAX-ACCESS read-only
			STATUS current
			DESCRIPTION
				"All thresholds of a sensor"
			::= { blade30SensorTargetEntry 3 }
		
 		b30UpperCritical OBJECT-TYPE
			SYNTAX DisplayString
			MAX-ACCESS read-write
			STATUS current
			DESCRIPTION
				"Upper critical thresholds"
			::= { blade30SensorTargetEntry 4 }
		
 		b30UpperNonCritical OBJECT-TYPE
			SYNTAX DisplayString
			MAX-ACCESS read-write
			STATUS current
			DESCRIPTION
				"Upper non-critical thresholds"
			::= { blade30SensorTargetEntry 5 }
		
 		b30UpperNonRecoverable OBJECT-TYPE
			SYNTAX DisplayString
			MAX-ACCESS read-write
			STATUS current
			DESCRIPTION
				"Upper non-recoverable thresholds"
			::= { blade30SensorTargetEntry 6 }
		
 		b30LowerNonCritical OBJECT-TYPE
			SYNTAX DisplayString
			MAX-ACCESS read-write
			STATUS current
			DESCRIPTION
				"Lower non-critical thresholds"
			::= { blade30SensorTargetEntry 7 }
		
 		b30LowerCritical OBJECT-TYPE
			SYNTAX DisplayString
			MAX-ACCESS read-write
			STATUS current
			DESCRIPTION
				"Lower critical thresholds"
			::= { blade30SensorTargetEntry 8 }
		
 		b30LowerNonRecoverable OBJECT-TYPE
			SYNTAX DisplayString
			MAX-ACCESS read-write
			STATUS current
			DESCRIPTION
				"Lower non-recoverable thresholds"
			::= { blade30SensorTargetEntry 9 }
		
 		b30SensorHealth OBJECT-TYPE
			SYNTAX INTEGER
				{
				ok(0),
				minor(1),
				major(2),
				critical(3)
				}
			MAX-ACCESS read-only
			STATUS current
			DESCRIPTION
				"b1Health information about a particular b1Location. 
				This will be one of the following:
				(0-ok, 1-minor, 2-major, 3-critical)"
			::= { blade30SensorTargetEntry 10 }
		
 		b30SensorHealthEvents OBJECT-TYPE
			SYNTAX DisplayString
			MAX-ACCESS read-only
			STATUS current
			DESCRIPTION
				"Events that contribute to the b1Health of the b1Location.  
				This is a list of events currently happening on the 
				b1Location."
			::= { blade30SensorTargetEntry 11 }
		
		
 		b30NegativeHysteresis OBJECT-TYPE
			SYNTAX DisplayString
			MAX-ACCESS read-write
			STATUS current
			DESCRIPTION
				"Get/Set the negativeHysteresis value."
			::= { blade30SensorTargetEntry 16 }
		
 		b30PositiveHysteresis OBJECT-TYPE
			SYNTAX DisplayString
			MAX-ACCESS read-write
			STATUS current
			DESCRIPTION
				"Get/Set the positiveHysteresis value."
			::= { blade30SensorTargetEntry 17 }
		
 		b30SensorType OBJECT-TYPE
			SYNTAX DisplayString
			MAX-ACCESS read-only
			STATUS current
			DESCRIPTION
				"Get the type of the sensor."
			::= { blade30SensorTargetEntry 18 }
		
 		b30SensorFRUInfo OBJECT-TYPE
			SYNTAX DisplayString
			MAX-ACCESS read-only
			STATUS current
			DESCRIPTION
				"Get the fruinfo of the sensor."
			::= { blade30SensorTargetEntry 19 }
		
 		blade30FruTable OBJECT-TYPE
			SYNTAX SEQUENCE OF Blade30FruEntry
			MAX-ACCESS not-accessible
			STATUS current
			DESCRIPTION
				"A table containing the list of FRU information."
			::= { blade30 2002 }
		
 		blade30FruEntry OBJECT-TYPE
			SYNTAX Blade30FruEntry
			MAX-ACCESS not-accessible
			STATUS current
			DESCRIPTION
				"Information about a particular current FRU."
			INDEX { b1fruNumber }
			::= { blade30FruTable 1 }
		
		Blade30FruEntry ::=
			SEQUENCE { 
				b30fruNumber
					INTEGER,
				b30FruHotSwapState
					DisplayString,
				b30FruLedProperties
					DisplayString,
				b30FRUControl
					INTEGER,
				b30FRULabel
					DisplayString,
				b30ResetReason
					DisplayString
			 }

 		b30fruNumber OBJECT-TYPE
			SYNTAX INTEGER
			MAX-ACCESS not-accessible
			STATUS current
			DESCRIPTION
				" "
			::= { blade30FruEntry 1 }
		
 		b30FruHotSwapState OBJECT-TYPE
			SYNTAX DisplayString
			MAX-ACCESS read-only
			STATUS current
			DESCRIPTION
				"Retrieve the hot swap state of the FRU from the 
				internally known hot swap states of blade1."
			::= { blade30FruEntry 3 }
		
 		b30FruLedProperties OBJECT-TYPE
			SYNTAX DisplayString
			MAX-ACCESS read-only
			STATUS current
			DESCRIPTION
				"Retrieves the LED support information from a FRU. Returns a comma separated
				list of LEDS and the number of FRU supported user LEDs."
			::= { blade30FruEntry 4 }

		

		b30FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade30FruEntry 9 }
		
 		b30FRULabel OBJECT-TYPE
			SYNTAX DisplayString
			MAX-ACCESS read-only
			STATUS current
			DESCRIPTION
				"Get fru label of blade1."
			::= { blade30FruEntry 10 }
		
 		b30ResetReason OBJECT-TYPE
			SYNTAX DisplayString
			MAX-ACCESS read-only
			STATUS current
			DESCRIPTION
				"Delete fru label of smm."
			::= { blade30FruEntry 11 }
		
 		blade30FruLedTable OBJECT-TYPE
			SYNTAX SEQUENCE OF Blade30FruLedEntry
			MAX-ACCESS not-accessible
			STATUS current
			DESCRIPTION
				"A table containing the list of led information."
			::= { blade30 2003 }
		
 		blade30FruLedEntry OBJECT-TYPE
			SYNTAX Blade30FruLedEntry
			MAX-ACCESS not-accessible
			STATUS current
			DESCRIPTION
				"Information about a particular current led."
			INDEX { b1FruID, b1FruLed }
			::= { blade30FruLedTable 1 }
		
		Blade30FruLedEntry ::=
			SEQUENCE { 
				b30FruID
					INTEGER,
				b30FruLed
					DisplayString,
				b30FruLedColorProps
					DisplayString,
				b30FruLedState
					DisplayString
			 }

 		b30FruID OBJECT-TYPE
			SYNTAX INTEGER
			MAX-ACCESS not-accessible
			STATUS current
			DESCRIPTION
				" "
			::= { blade30FruLedEntry 1 }
		
 		b30FruLed OBJECT-TYPE
			SYNTAX DisplayString
			MAX-ACCESS not-accessible
			STATUS current
			DESCRIPTION
				" "
			::= { blade30FruLedEntry 2 }
		
 		b30FruLedColorProps OBJECT-TYPE
			SYNTAX DisplayString
			MAX-ACCESS read-only
			STATUS current
			DESCRIPTION
				"Finds out what colors are supported by the LED"
			::= { blade30FruLedEntry 3 }
		
 		b30FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade30FruLedEntry 4 }
		
 		blade30FruDescriptionTable OBJECT-TYPE
			SYNTAX SEQUENCE OF Blade30FruDescriptionEntry
			MAX-ACCESS not-accessible
			STATUS current
			DESCRIPTION
				"A table containing the list of Blade1 FRU information."
			::= { blade30 2004 }
		
 		blade30FruDescriptionEntry OBJECT-TYPE
			SYNTAX Blade30FruDescriptionEntry
			MAX-ACCESS not-accessible
			STATUS current
			DESCRIPTION
				"Information about a particular current FRU."
			INDEX { b1fruNum }
			::= { blade30FruDescriptionTable 1 }
		
		Blade30FruDescriptionEntry ::=
			SEQUENCE { 
				b30fruNum
					INTEGER,
				b30fruBoardDescription
					DisplayString,
				b30fruBoardManufacturer
					DisplayString,
				b30fruBoardPartNumber
					DisplayString,
				b30fruBoardSerialNumber
					DisplayString,
				b30fruBoardManufactureDate
					DisplayString,
				b30fruProductDescription
					DisplayString,
				b30fruProductManufacturer
					DisplayString,
				b30fruProductPartNumber
					DisplayString,
				b30fruProductSerialNumber
					DisplayString,
				b30fruProductRevision
					DisplayString,
				b30fruAll
					DisplayString
			 }

 		b30fruNum OBJECT-TYPE
			SYNTAX INTEGER
			MAX-ACCESS not-accessible
			STATUS current
			DESCRIPTION
				"blade1 FRU's INDEX"
			::= { blade30FruDescriptionEntry 1 }
		
 		b30fruBoardDescription OBJECT-TYPE
			SYNTAX DisplayString
			MAX-ACCESS read-only
			STATUS current
			DESCRIPTION
				"Used to read the Board Description from the blade1 fru."
			::= { blade30FruDescriptionEntry 2 }
		
 		b30fruBoardManufacturer OBJECT-TYPE
			SYNTAX DisplayString
			MAX-ACCESS read-only
			STATUS current
			DESCRIPTION
				"Used to read the Board Manufacturer from the blade1 fru."
			::= { blade30FruDescriptionEntry 3 }
		
 		b30fruBoardPartNumber OBJECT-TYPE
			SYNTAX DisplayString
			MAX-ACCESS read-only
			STATUS current
			DESCRIPTION
				"Used to read the Board Part Number from the blade1 fru."
			::= { blade30FruDescriptionEntry 4 }
		
 		b30fruBoardSerialNumber OBJECT-TYPE
			SYNTAX DisplayString
			MAX-ACCESS read-only
			STATUS current
			DESCRIPTION
				"Used to read the Board Serial Number from the blade1 fru."
			::= { blade30FruDescriptionEntry 5 }
		
 		b30fruBoardManufactureDate OBJECT-TYPE
			SYNTAX DisplayString
			MAX-ACCESS read-only
			STATUS current
			DESCRIPTION
				"Used to read the Board Manufacture Date from the blade1 fru."
			::= { blade30FruDescriptionEntry 6 }
		
 		b30fruProductDescription OBJECT-TYPE
			SYNTAX DisplayString
			MAX-ACCESS read-only
			STATUS current
			DESCRIPTION
				"Used to read the Product Description from the blade1 fru."
			::= { blade30FruDescriptionEntry 7 }
		
 		b30fruProductManufacturer OBJECT-TYPE
			SYNTAX DisplayString
			MAX-ACCESS read-only
			STATUS current
			DESCRIPTION
				"Used to read the Product Manufacturer from the blade1 fru."
			::= { blade30FruDescriptionEntry 8 }
		
 		b30fruProductPartNumber OBJECT-TYPE
			SYNTAX DisplayString
			MAX-ACCESS read-only
			STATUS current
			DESCRIPTION
				"Used to read the Product Part Number from the blade1 fru."
			::= { blade30FruDescriptionEntry 9 }
		
 		b30fruProductSerialNumber OBJECT-TYPE
			SYNTAX DisplayString
			MAX-ACCESS read-only
			STATUS current
			DESCRIPTION
				"Used to read the Product Serial Number from the blade1 fru."
			::= { blade30FruDescriptionEntry 10 }
		
 		b30fruProductRevision OBJECT-TYPE
			SYNTAX DisplayString
			MAX-ACCESS read-only
			STATUS current
			DESCRIPTION
				"Used to read the Product Revision from the blade1 fru."
			::= { blade30FruDescriptionEntry 13 }
		
 		b30fruAll OBJECT-TYPE
			SYNTAX DisplayString
			MAX-ACCESS read-only
			STATUS current
			DESCRIPTION
				"Used to read the fru info all."
			::= { blade30FruDescriptionEntry 14 }
		
		blade30CPUTable OBJECT-TYPE
			SYNTAX SEQUENCE OF Blade30CPUEntry
			MAX-ACCESS not-accessible
			STATUS current
			DESCRIPTION
				"A table containing the list of Blade1 FRU information."
			::= { blade30 2006 }
		
		blade30CPUEntry OBJECT-TYPE
			SYNTAX Blade30CPUEntry
			MAX-ACCESS not-accessible
			STATUS current
			DESCRIPTION
				"Information about a particular current FRU."
			INDEX { b30CPUIndex }
			::= { blade30CPUTable 1 }
		
		Blade30CPUEntry ::=
			SEQUENCE { 
				b30CPUIndex
					INTEGER,
				b30CPUMark
					DisplayString,
				b30CPUInfo
					DisplayString,
				b30CPUPresent
					INTEGER,
				b30CPUHealth
					INTEGER,
				b30CPULocation
					DisplayString
			 }

		b30CPUIndex OBJECT-TYPE
			SYNTAX INTEGER
			MAX-ACCESS not-accessible
			STATUS current
			DESCRIPTION
				"CPU INDEX"
			::= { blade30CPUEntry 1 }
		
		b30CPUMark OBJECT-TYPE
			SYNTAX DisplayString
			MAX-ACCESS read-only
			STATUS current
			DESCRIPTION
				"Get the CPU silk-screen."
			::= { blade30CPUEntry 2 }
		
		b30CPUInfo OBJECT-TYPE
			SYNTAX DisplayString
			MAX-ACCESS read-only
			STATUS current
			DESCRIPTION
				"Get the CPU description of vendor, type and frequency."
			::= { blade30CPUEntry 3 }
		
		b30CPUPresent OBJECT-TYPE
			SYNTAX INTEGER
			MAX-ACCESS read-only
			STATUS current
			DESCRIPTION
				"Get the CPU presence status."
			::= { blade30CPUEntry 4 }
		
		b30CPUHealth OBJECT-TYPE
			SYNTAX INTEGER
			MAX-ACCESS read-only
			STATUS current
			DESCRIPTION
				"Get the CPU health status."
			::= { blade30CPUEntry 5 }
		
		b30CPULocation OBJECT-TYPE
			SYNTAX DisplayString
			MAX-ACCESS read-only
			STATUS current
			DESCRIPTION
				"Get the CPU location."
			::= { blade30CPUEntry 6 }
		
		blade30MemoryTable OBJECT-TYPE
			SYNTAX SEQUENCE OF Blade30MemoryEntry
			MAX-ACCESS not-accessible
			STATUS current
			DESCRIPTION
				"A table containing the list of Blade1 FRU information."
			::= { blade30 2007 }
		
		blade30MemoryEntry OBJECT-TYPE
			SYNTAX Blade30MemoryEntry
			MAX-ACCESS not-accessible
			STATUS current
			DESCRIPTION
				"Information about a particular current FRU."
			INDEX { b30MEMIndex }
			::= { blade30MemoryTable 1 }
		
		Blade30MemoryEntry ::=
			SEQUENCE { 
				b30MEMIndex
					INTEGER,
				b30MEMMark
					DisplayString,
				b30MEMInfo
					DisplayString,
				b30MEMPresent
					INTEGER,
				b30MEMHealth
					INTEGER,
				b30MEMLocation
					DisplayString
			 }

		b30MEMIndex OBJECT-TYPE
			SYNTAX INTEGER
			MAX-ACCESS not-accessible
			STATUS current
			DESCRIPTION
				"MEMORY INDEX"
			::= { blade30MemoryEntry 1 }
		
		b30MEMMark OBJECT-TYPE
			SYNTAX DisplayString
			MAX-ACCESS read-only
			STATUS current
			DESCRIPTION
				"Get the memory silk-screen."
			::= { blade30MemoryEntry 2 }
		
		b30MEMInfo OBJECT-TYPE
			SYNTAX DisplayString
			MAX-ACCESS read-only
			STATUS current
			DESCRIPTION
				"Get the memory description of vendor, frequency and capacity."
			::= { blade30MemoryEntry 3 }
		
		b30MEMPresent OBJECT-TYPE
			SYNTAX INTEGER
			MAX-ACCESS read-only
			STATUS current
			DESCRIPTION
				"Get the memory presence status."
			::= { blade30MemoryEntry 4 }
		
		b30MEMHealth OBJECT-TYPE
			SYNTAX INTEGER
			MAX-ACCESS read-only
			STATUS current
			DESCRIPTION
				"Get the memory health status."
			::= { blade30MemoryEntry 5 }
		
		b30MEMLocation OBJECT-TYPE
			SYNTAX DisplayString
			MAX-ACCESS read-only
			STATUS current
			DESCRIPTION
				"Get the memory location."
			::= { blade30MemoryEntry 6 }
		
		blade30MezzTable OBJECT-TYPE
			SYNTAX SEQUENCE OF Blade30MezzEntry
			MAX-ACCESS not-accessible
			STATUS current
			DESCRIPTION
				"A table containing the list of Blade1 FRU information."
			::= { blade30 2008 }
		
		blade30MezzEntry OBJECT-TYPE
			SYNTAX Blade30MezzEntry
			MAX-ACCESS not-accessible
			STATUS current
			DESCRIPTION
				"Information about a particular current FRU."
			INDEX { b30MezzIndex }
			::= { blade30MezzTable 1 }
		
		Blade30MezzEntry ::=
			SEQUENCE { 
				b30MezzIndex
					INTEGER,
				b30MezzMark
					DisplayString,
				b30MezzInfo
					DisplayString,
				b30MezzPresent
					INTEGER,
				b30MezzHealth
					INTEGER,
				b30MezzLocation
					DisplayString,
				b30MezzMac
					DisplayString
			 }

		b30MezzIndex OBJECT-TYPE
			SYNTAX INTEGER
			MAX-ACCESS not-accessible
			STATUS current
			DESCRIPTION
				"MEZZ INDEX"
			::= { blade30MezzEntry 1 }
		
		b30MezzMark OBJECT-TYPE
			SYNTAX DisplayString
			MAX-ACCESS read-only
			STATUS current
			DESCRIPTION
				"Get the MEZZ silk-screen."
			::= { blade30MezzEntry 2 }
		
		b30MezzInfo OBJECT-TYPE
			SYNTAX DisplayString
			MAX-ACCESS read-only
			STATUS current
			DESCRIPTION
				"Get the MEZZ description of type."
			::= { blade30MezzEntry 3 }
		
		b30MezzPresent OBJECT-TYPE
			SYNTAX INTEGER
			MAX-ACCESS read-only
			STATUS current
			DESCRIPTION
				"Get the MEZZ presence status."
			::= { blade30MezzEntry 4 }
		
		b30MezzHealth OBJECT-TYPE
			SYNTAX INTEGER
			MAX-ACCESS read-only
			STATUS current
			DESCRIPTION
				"Get the MEZZ health status."
			::= { blade30MezzEntry 5 }
		
		b30MezzLocation OBJECT-TYPE
			SYNTAX DisplayString
			MAX-ACCESS read-only
			STATUS current
			DESCRIPTION
				"Get the MEZZ location."
			::= { blade30MezzEntry 6 }
		
		b30MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade30MezzEntry 7 }
		
		blade30DiskTable OBJECT-TYPE
			SYNTAX SEQUENCE OF Blade30DiskEntry
			MAX-ACCESS not-accessible
			STATUS current
			DESCRIPTION
				"A table containing the list of Blade1 FRU information."
			::= { blade30 2009 }
		
		blade30DiskEntry OBJECT-TYPE
			SYNTAX Blade30DiskEntry
			MAX-ACCESS not-accessible
			STATUS current
			DESCRIPTION
				"Information about a particular current FRU."
			INDEX { b30DiskIndex }
			::= { blade30DiskTable 1 }
		
		Blade30DiskEntry ::=
			SEQUENCE { 
				b30DiskIndex
					INTEGER,
				b30DiskMark
					DisplayString,
				b30DiskInfo
					DisplayString,
				b30DiskPresent
					INTEGER,
				b30DiskHealth
					INTEGER,
				b30DiskLocation
					DisplayString
			 }

		b30DiskIndex OBJECT-TYPE
			SYNTAX INTEGER
			MAX-ACCESS not-accessible
			STATUS current
			DESCRIPTION
				"DISK INDEX"
			::= { blade30DiskEntry 1 }
		
		b30DiskMark OBJECT-TYPE
			SYNTAX DisplayString
			MAX-ACCESS read-only
			STATUS current
			DESCRIPTION
				"Get the disk silk-screen."
			::= { blade30DiskEntry 2 }
		
		b30DiskInfo OBJECT-TYPE
			SYNTAX DisplayString
			MAX-ACCESS read-only
			STATUS current
			DESCRIPTION
				"Get the disk description of vendor, capacity and speed."
			::= { blade30DiskEntry 3 }
		
		b30DiskPresent OBJECT-TYPE
			SYNTAX INTEGER
			MAX-ACCESS read-only
			STATUS current
			DESCRIPTION
				"Get the disk presence status."
			::= { blade30DiskEntry 4 }
		
		b30DiskHealth OBJECT-TYPE
			SYNTAX INTEGER
			MAX-ACCESS read-only
			STATUS current
			DESCRIPTION
				"Get the disk health status."
			::= { blade30DiskEntry 5 }
		
		b30DiskLocation OBJECT-TYPE
			SYNTAX DisplayString
			MAX-ACCESS read-only
			STATUS current
			DESCRIPTION
				"Get the disk location."
			::= { blade30DiskEntry 6 }
		
		blade30SecretKvmVmmTable OBJECT-TYPE
			SYNTAX SEQUENCE OF Blade30SecretKvmVmmEntry
			MAX-ACCESS not-accessible
			STATUS current
			DESCRIPTION
				"A table containing the list of Blade30 KVM&VMM secret information."
			::= { blade30 2010 }

		blade30SecretKvmVmmEntry OBJECT-TYPE
			SYNTAX Blade30SecretKvmVmmEntry
			MAX-ACCESS not-accessible
			STATUS current
			DESCRIPTION
				"Information about a particular current KVM&VMM."
			INDEX { b30SecretKvmVmmIndex }
			::= { blade30SecretKvmVmmTable 1 }
		Blade30SecretKvmVmmEntry ::=
			SEQUENCE { 
				b30SecretKvmVmmIndex
					INTEGER,
				b30SecretKvmState
					INTEGER,
				b30SecretVmmState
					INTEGER,
				b30MMSecretVmmKey
					DisplayString,
				b30SecretVmmKey
					DisplayString
			 }
		b30SecretKvmVmmIndex OBJECT-TYPE
			SYNTAX INTEGER
			MAX-ACCESS not-accessible
			STATUS current
			DESCRIPTION
				"KVM&VMM INDEX."
			::= { blade30SecretKvmVmmEntry 1 }
		b30SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade30SecretKvmVmmEntry 2 }
		b30SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade30SecretKvmVmmEntry 3 }
		b30MMSecretVmmKey OBJECT-TYPE
			SYNTAX DisplayString
			MAX-ACCESS read-only
			STATUS current
			DESCRIPTION
				"Get the MM secret VMM key."
			::= { blade30SecretKvmVmmEntry 4 }
		b30SecretVmmKey OBJECT-TYPE
			SYNTAX DisplayString
			MAX-ACCESS read-write
			STATUS current
			DESCRIPTION
				"Set the secret VMM key."
			::= { blade30SecretKvmVmmEntry 5 }
		blade31 OBJECT IDENTIFIER ::= { blades 31 }

		
 		b31DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade31 4 }
		
 		b31PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade31 5 }
		
 		b31Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade31 6 }

		
 		b31Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b11Health information about a particular b11Location. 
				This will be one of the following:
				(0-ok, 1-minor, 2-major, 3-majorandminor,4-critical,5-criticalandminor,6-criticalandmajor,7-criticalandmajorandminor)"
			::= { blade31 8 }
		
 		b31HealthEvents OBJECT-TYPE
			SYNTAX DisplayString
			MAX-ACCESS read-only
			STATUS current
			DESCRIPTION
				"Events that contribute to the b11Health of the b11Location.  
				This is a list of events currently happening on the 
				b11Location."
			::= { blade31 9 }
		
 		b31ClearSEL OBJECT-TYPE
			SYNTAX INTEGER { clear(1) }
			MAX-ACCESS read-write
			STATUS current
			DESCRIPTION
				"Clean the BMC's SEL on the board."
			::= { blade31 12 }
		
 		b31ExDiskBoardPresence OBJECT-TYPE
			SYNTAX INTEGER
				{
				not-present(0),
				present(1)
				}
			MAX-ACCESS read-only
			STATUS current
			DESCRIPTION
				"Used to find out if the extended disk board is present.
				0 - not present
				1 - present"
			::= { blade31 14 }
		
 		b31BladeVersion OBJECT-TYPE
			SYNTAX DisplayString
			MAX-ACCESS read-only
			STATUS current
			DESCRIPTION
				"display the Version of board11."
			::= { blade31 20 }
		
 		b31MACAddress OBJECT-TYPE
			SYNTAX DisplayString
			MAX-ACCESS read-only
			STATUS current
			DESCRIPTION
				"display the MACAddress of board11."
			::= { blade31 21 }
		
				
							
		
 		b31Safepwofftime OBJECT-TYPE
			SYNTAX INTEGER
			MAX-ACCESS read-write
			STATUS current
			DESCRIPTION
				"the safe poweroff time.
				"
			::= { blade31 26 }
		
 		b31BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2] 
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]          
				6=Force boot into BIOS Setup
				15=Force boot from Floppy/primary removable media           
				
				"
			::= { blade31 32 }
		
 		b31Systeminfo OBJECT-TYPE
			SYNTAX DisplayString
			MAX-ACCESS read-write
			STATUS current
			DESCRIPTION
				"display the system information of board11."
			::= { blade31 36 }

		
 		b31SystemProperties OBJECT-TYPE
			SYNTAX DisplayString
			MAX-ACCESS read-only
			STATUS current
			DESCRIPTION
				"Get the power of blade1."
			::= { blade31 39 }
		
 		b31BiosCfg OBJECT-TYPE
			SYNTAX DisplayString
			MAX-ACCESS read-write
			STATUS current
			DESCRIPTION
				"Get the power of blade1."
			::= { blade31 40 }
		
 		b31WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade31 41 }
		
 		b31RealTimePower OBJECT-TYPE
			SYNTAX INTEGER
			MAX-ACCESS read-only
			STATUS current
			DESCRIPTION
				" "
			::= { blade31 43 }
		
 		b31PowerCapping OBJECT-TYPE
			SYNTAX DisplayString
			MAX-ACCESS read-write
			STATUS current
			DESCRIPTION
				" "
			::= { blade31 44 }
		
 		b31Powerreference OBJECT-TYPE
			SYNTAX INTEGER
			MAX-ACCESS read-only
			STATUS current
			DESCRIPTION
				" "
			::= { blade31 45 }
		
 		b31ClearBiosConfig OBJECT-TYPE
			SYNTAX INTEGER
			MAX-ACCESS read-write
			STATUS current
			DESCRIPTION
				" "
			::= { blade31 46 }
		
 		b31BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade31 47 }
		
 		b31BmcUserAdd OBJECT-TYPE
			SYNTAX DisplayString
			MAX-ACCESS read-write
			STATUS current
			DESCRIPTION
				"Used to Add the BMC User
				settable format:
				username,passwd"
			::= { blade31 48 }
		
 		b31BmcUserDel OBJECT-TYPE
			SYNTAX DisplayString
			MAX-ACCESS read-write
			STATUS current
			DESCRIPTION
				"Used to Del the BMC User
				settable format:
				username"
			::= { blade31 49 }
		
 		b31BmcUserPasswd OBJECT-TYPE
			SYNTAX DisplayString
			MAX-ACCESS read-write
			STATUS current
			DESCRIPTION
				"Used to Change the BMC User Passwd
				settable format:
				username,passwd"
			::= { blade31 50 }
		
 		b31BmcUserpropertychg OBJECT-TYPE
			SYNTAX DisplayString
			MAX-ACCESS read-write
			STATUS current
			DESCRIPTION
				"Used to Change the BMC User Property
				settable format:
				username,property"
			::= { blade31 51 }
		
 		b31BmcGateway OBJECT-TYPE
			SYNTAX DisplayString
			MAX-ACCESS read-write
			STATUS current
			DESCRIPTION
				"Read or set the gateway."
			::= { blade31 52 }
		
 		b31SlotBitmap OBJECT-TYPE
			SYNTAX INTEGER
			MAX-ACCESS read-only
			STATUS current
			DESCRIPTION
				" "
			::= { blade31 55 }
		
		b31systemGuid OBJECT-TYPE
			SYNTAX DisplayString
			MAX-ACCESS read-only
			STATUS current
			DESCRIPTION
				" "
			::= { blade31 56 }
		
		b31ProductName OBJECT-TYPE
			SYNTAX DisplayString
			MAX-ACCESS read-only
			STATUS current
			DESCRIPTION
				"display the Version of board11."
			::= { blade31 57 }
			
		b31BundleVersion OBJECT-TYPE
			SYNTAX DisplayString
			MAX-ACCESS read-write
			STATUS current
			DESCRIPTION
				"Get or set the board31 bundle version."
			::= { blade31 58 }

 		blade31SensorTargetTable OBJECT-TYPE
			SYNTAX SEQUENCE OF Blade31SensorTargetEntry
			MAX-ACCESS not-accessible
			STATUS current
			DESCRIPTION
				"A table containing the list of sensor information."
			::= { blade31 2001 }
		
 		blade31SensorTargetEntry OBJECT-TYPE
			SYNTAX Blade31SensorTargetEntry
			MAX-ACCESS not-accessible
			STATUS current
			DESCRIPTION
				"Information about a particular current sensor."
			INDEX { b11Target }
			::= { blade31SensorTargetTable 1 }
		
		Blade31SensorTargetEntry ::=
			SEQUENCE { 
				b31Target
					DisplayString,
				b31Current
					DisplayString,
				b31ThresholdsAll
					DisplayString,
				b31UpperCritical
					DisplayString,
				b31UpperNonCritical
					DisplayString,
				b31UpperNonRecoverable
					DisplayString,
				b31LowerNonCritical
					DisplayString,
				b31LowerCritical
					DisplayString,
				b31LowerNonRecoverable
					DisplayString,
				b31SensorHealth
					INTEGER,
				b31SensorHealthEvents
					DisplayString,
				b31NegativeHysteresis
					DisplayString,
				b31PositiveHysteresis
					DisplayString,
				b31SensorType
					DisplayString,
				b31SensorFRUInfo
					DisplayString
			 }

 		b31Target OBJECT-TYPE
			SYNTAX DisplayString
			MAX-ACCESS not-accessible
			STATUS current
			DESCRIPTION
				"sensor Name"
			::= { blade31SensorTargetEntry 1 }
		
 		b31Current OBJECT-TYPE
			SYNTAX DisplayString
			MAX-ACCESS read-only
			STATUS current
			DESCRIPTION
				"Display the current value of a sensor."
			::= { blade31SensorTargetEntry 2 }
		
 		b31ThresholdsAll OBJECT-TYPE
			SYNTAX DisplayString
			MAX-ACCESS read-only
			STATUS current
			DESCRIPTION
				"All thresholds of a sensor"
			::= { blade31SensorTargetEntry 3 }
		
 		b31UpperCritical OBJECT-TYPE
			SYNTAX DisplayString
			MAX-ACCESS read-write
			STATUS current
			DESCRIPTION
				"Upper critical thresholds"
			::= { blade31SensorTargetEntry 4 }
		
 		b31UpperNonCritical OBJECT-TYPE
			SYNTAX DisplayString
			MAX-ACCESS read-write
			STATUS current
			DESCRIPTION
				"Upper non-critical thresholds"
			::= { blade31SensorTargetEntry 5 }
		
 		b31UpperNonRecoverable OBJECT-TYPE
			SYNTAX DisplayString
			MAX-ACCESS read-write
			STATUS current
			DESCRIPTION
				"Upper non-recoverable thresholds"
			::= { blade31SensorTargetEntry 6 }
		
 		b31LowerNonCritical OBJECT-TYPE
			SYNTAX DisplayString
			MAX-ACCESS read-write
			STATUS current
			DESCRIPTION
				"Lower non-critical thresholds"
			::= { blade31SensorTargetEntry 7 }
		
 		b31LowerCritical OBJECT-TYPE
			SYNTAX DisplayString
			MAX-ACCESS read-write
			STATUS current
			DESCRIPTION
				"Lower critical thresholds"
			::= { blade31SensorTargetEntry 8 }
		
 		b31LowerNonRecoverable OBJECT-TYPE
			SYNTAX DisplayString
			MAX-ACCESS read-write
			STATUS current
			DESCRIPTION
				"Lower non-recoverable thresholds"
			::= { blade31SensorTargetEntry 9 }
		
 		b31SensorHealth OBJECT-TYPE
			SYNTAX INTEGER
				{
				ok(0),
				minor(1),
				major(2),
				critical(3)
				}
			MAX-ACCESS read-only
			STATUS current
			DESCRIPTION
				"b11Health information about a particular b11Location. 
				This will be one of the following:
				(0-ok, 1-minor, 2-major, 3-critical)"
			::= { blade31SensorTargetEntry 10 }
		
 		b31SensorHealthEvents OBJECT-TYPE
			SYNTAX DisplayString
			MAX-ACCESS read-only
			STATUS current
			DESCRIPTION
				"Events that contribute to the b11Health of the b11Location.  
				This is a list of events currently happening on the 
				b11Location."
			::= { blade31SensorTargetEntry 11 }
		
		
 		b31NegativeHysteresis OBJECT-TYPE
			SYNTAX DisplayString
			MAX-ACCESS read-write
			STATUS current
			DESCRIPTION
				"Get/Set the negativeHysteresis value"
			::= { blade31SensorTargetEntry 16 }
		
 		b31PositiveHysteresis OBJECT-TYPE
			SYNTAX DisplayString
			MAX-ACCESS read-write
			STATUS current
			DESCRIPTION
				"Get/Set the positiveHysteresis value."
			::= { blade31SensorTargetEntry 17 }
		
 		b31SensorType OBJECT-TYPE
			SYNTAX DisplayString
			MAX-ACCESS read-only
			STATUS current
			DESCRIPTION
				"Get the type of the sensor."
			::= { blade31SensorTargetEntry 18 }
		
 		b31SensorFRUInfo OBJECT-TYPE
			SYNTAX DisplayString
			MAX-ACCESS read-only
			STATUS current
			DESCRIPTION
				"Get the fruinfo of the sensor."
			::= { blade31SensorTargetEntry 19 }
		
 		blade31FruTable OBJECT-TYPE
			SYNTAX SEQUENCE OF Blade31FruEntry
			MAX-ACCESS not-accessible
			STATUS current
			DESCRIPTION
				"A table containing the list of FRU information."
			::= { blade31 2002 }
		
 		blade31FruEntry OBJECT-TYPE
			SYNTAX Blade31FruEntry
			MAX-ACCESS not-accessible
			STATUS current
			DESCRIPTION
				"Information about a particular current FRU."
			INDEX { b11fruNumber }
			::= { blade31FruTable 1 }
		
		Blade31FruEntry ::=
			SEQUENCE { 
				b31fruNumber
					INTEGER,
				b31FruHotSwapState
					DisplayString,
				b31FruLedProperties
					DisplayString,
				b31FRUControl
					INTEGER,
				b31FRULabel
					DisplayString,
				b31ResetReason
					DisplayString
			 }

 		b31fruNumber OBJECT-TYPE
			SYNTAX INTEGER
			MAX-ACCESS not-accessible
			STATUS current
			DESCRIPTION
				" "
			::= { blade31FruEntry 1 }
		
 		b31FruHotSwapState OBJECT-TYPE
			SYNTAX DisplayString
			MAX-ACCESS read-only
			STATUS current
			DESCRIPTION
				"Retrieve the hot swap state of the FRU from the 
				internally known hot swap states of blade11."
			::= { blade31FruEntry 3 }
		
 		b31FruLedProperties OBJECT-TYPE
			SYNTAX DisplayString
			MAX-ACCESS read-only
			STATUS current
			DESCRIPTION
				"Retrieves the LED support information from a FRU. Returns a comma separated
				list of LEDS and the number of FRU supported user LEDs."
			::= { blade31FruEntry 4 }

		

		b31FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade31FruEntry 9 }
		
 		b31FRULabel OBJECT-TYPE
			SYNTAX DisplayString
			MAX-ACCESS read-only
			STATUS current
			DESCRIPTION
				"Get fru label of blade11."
			::= { blade31FruEntry 10 }
		
 		b31ResetReason OBJECT-TYPE
			SYNTAX DisplayString
			MAX-ACCESS read-only
			STATUS current
			DESCRIPTION
				"Delete fru label of smm."
			::= { blade31FruEntry 11 }
		
 		blade31FruLedTable OBJECT-TYPE
			SYNTAX SEQUENCE OF Blade31FruLedEntry
			MAX-ACCESS not-accessible
			STATUS current
			DESCRIPTION
				"A table containing the list of led information."
			::= { blade31 2003 }
		
 		blade31FruLedEntry OBJECT-TYPE
			SYNTAX Blade31FruLedEntry
			MAX-ACCESS not-accessible
			STATUS current
			DESCRIPTION
				"Information about a particular current led."
			INDEX { b11FruID, b11FruLed }
			::= { blade31FruLedTable 1 }
		
		Blade31FruLedEntry ::=
			SEQUENCE { 
				b31FruID
					INTEGER,
				b31FruLed
					DisplayString,
				b31FruLedColorProps
					DisplayString,
				b31FruLedState
					DisplayString
			 }

 		b31FruID OBJECT-TYPE
			SYNTAX INTEGER
			MAX-ACCESS not-accessible
			STATUS current
			DESCRIPTION
				" "
			::= { blade31FruLedEntry 1 }
		
 		b31FruLed OBJECT-TYPE
			SYNTAX DisplayString
			MAX-ACCESS not-accessible
			STATUS current
			DESCRIPTION
				" "
			::= { blade31FruLedEntry 2 }
		
 		b31FruLedColorProps OBJECT-TYPE
			SYNTAX DisplayString
			MAX-ACCESS read-only
			STATUS current
			DESCRIPTION
				"Finds out what colors are supported by the LED"
			::= { blade31FruLedEntry 3 }
		
 		b31FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade31FruLedEntry 4 }
		
 		blade31FruDescriptionTable OBJECT-TYPE
			SYNTAX SEQUENCE OF Blade31FruDescriptionEntry
			MAX-ACCESS not-accessible
			STATUS current
			DESCRIPTION
				"A table containing the list of blade11 FRU information."
			::= { blade31 2004 }
		
 		blade31FruDescriptionEntry OBJECT-TYPE
			SYNTAX Blade31FruDescriptionEntry
			MAX-ACCESS not-accessible
			STATUS current
			DESCRIPTION
				"Information about a particular current FRU."
			INDEX { b11fruNum }
			::= { blade31FruDescriptionTable 1 }
		
		Blade31FruDescriptionEntry ::=
			SEQUENCE { 
				b31fruNum
					INTEGER,
				b31fruBoardDescription
					DisplayString,
				b31fruBoardManufacturer
					DisplayString,
				b31fruBoardPartNumber
					DisplayString,
				b31fruBoardSerialNumber
					DisplayString,
				b31fruBoardManufactureDate
					DisplayString,
				b31fruProductDescription
					DisplayString,
				b31fruProductManufacturer
					DisplayString,
				b31fruProductPartNumber
					DisplayString,
				b31fruProductSerialNumber
					DisplayString,
				b31fruProductRevision
					DisplayString,
				b31fruAll
					DisplayString
			 }

 		b31fruNum OBJECT-TYPE
			SYNTAX INTEGER
			MAX-ACCESS not-accessible
			STATUS current
			DESCRIPTION
				"blade11 FRU's INDEX"
			::= { blade31FruDescriptionEntry 1 }
		
 		b31fruBoardDescription OBJECT-TYPE
			SYNTAX DisplayString
			MAX-ACCESS read-only
			STATUS current
			DESCRIPTION
				"Used to read the Board Description from the blade11 fru."
			::= { blade31FruDescriptionEntry 2 }
		
 		b31fruBoardManufacturer OBJECT-TYPE
			SYNTAX DisplayString
			MAX-ACCESS read-only
			STATUS current
			DESCRIPTION
				"Used to read the Board Manufacturer from the bladef11 fru."
			::= { blade31FruDescriptionEntry 3 }
		
 		b31fruBoardPartNumber OBJECT-TYPE
			SYNTAX DisplayString
			MAX-ACCESS read-only
			STATUS current
			DESCRIPTION
				"Used to read the Board Part Number from the blade11 fru."
			::= { blade31FruDescriptionEntry 4 }
		
 		b31fruBoardSerialNumber OBJECT-TYPE
			SYNTAX DisplayString
			MAX-ACCESS read-only
			STATUS current
			DESCRIPTION
				"Used to read the Board Serial Number from the blade11 fru."
			::= { blade31FruDescriptionEntry 5 }
		
 		b31fruBoardManufactureDate OBJECT-TYPE
			SYNTAX DisplayString
			MAX-ACCESS read-only
			STATUS current
			DESCRIPTION
				"Used to read the Board Manufacture Date from the blade11 fru."
			::= { blade31FruDescriptionEntry 6 }
		
 		b31fruProductDescription OBJECT-TYPE
			SYNTAX DisplayString
			MAX-ACCESS read-only
			STATUS current
			DESCRIPTION
				"Used to read the Product Description from the blade11 fru."
			::= { blade31FruDescriptionEntry 7 }
		
 		b31fruProductManufacturer OBJECT-TYPE
			SYNTAX DisplayString
			MAX-ACCESS read-only
			STATUS current
			DESCRIPTION
				"Used to read the Product Manufacturer from the blade11 fru."
			::= { blade31FruDescriptionEntry 8 }
		
 		b31fruProductPartNumber OBJECT-TYPE
			SYNTAX DisplayString
			MAX-ACCESS read-only
			STATUS current
			DESCRIPTION
				"Used to read the Product Part Number from the blade11 fru."
			::= { blade31FruDescriptionEntry 9 }
		
 		b31fruProductSerialNumber OBJECT-TYPE
			SYNTAX DisplayString
			MAX-ACCESS read-only
			STATUS current
			DESCRIPTION
				"Used to read the Product Serial Number from the blade11 fru."
			::= { blade31FruDescriptionEntry 10 }
		
 		b31fruProductRevision OBJECT-TYPE
			SYNTAX DisplayString
			MAX-ACCESS read-only
			STATUS current
			DESCRIPTION
				"Used to read the Product Revision from the blade11 fru."
			::= { blade31FruDescriptionEntry 13 }
		
 		b31fruAll OBJECT-TYPE
			SYNTAX DisplayString
			MAX-ACCESS read-only
			STATUS current
			DESCRIPTION
				"Used to read the fru info all."
			::= { blade31FruDescriptionEntry 14 }
		
		blade31CPUTable OBJECT-TYPE
			SYNTAX SEQUENCE OF Blade31CPUEntry
			MAX-ACCESS not-accessible
			STATUS current
			DESCRIPTION
				"A table containing the list of Blade1 FRU information."
			::= { blade31 2006 }
		
		blade31CPUEntry OBJECT-TYPE
			SYNTAX Blade31CPUEntry
			MAX-ACCESS not-accessible
			STATUS current
			DESCRIPTION
				"Information about a particular current FRU."
			INDEX { b31CPUIndex }
			::= { blade31CPUTable 1 }
		
		Blade31CPUEntry ::=
			SEQUENCE { 
				b31CPUIndex
					INTEGER,
				b31CPUMark
					DisplayString,
				b31CPUInfo
					DisplayString,
				b31CPUPresent
					INTEGER,
				b31CPUHealth
					INTEGER,
				b31CPULocation
					DisplayString
			 }

		b31CPUIndex OBJECT-TYPE
			SYNTAX INTEGER
			MAX-ACCESS not-accessible
			STATUS current
			DESCRIPTION
				"CPU INDEX"
			::= { blade31CPUEntry 1 }
		
		b31CPUMark OBJECT-TYPE
			SYNTAX DisplayString
			MAX-ACCESS read-only
			STATUS current
			DESCRIPTION
				"Get the CPU silk-screen."
			::= { blade31CPUEntry 2 }
		
		b31CPUInfo OBJECT-TYPE
			SYNTAX DisplayString
			MAX-ACCESS read-only
			STATUS current
			DESCRIPTION
				"Get the CPU description of vendor, type and frequency."
			::= { blade31CPUEntry 3 }
		
		b31CPUPresent OBJECT-TYPE
			SYNTAX INTEGER
			MAX-ACCESS read-only
			STATUS current
			DESCRIPTION
				"Get the CPU presence status."
			::= { blade31CPUEntry 4 }
		
		b31CPUHealth OBJECT-TYPE
			SYNTAX INTEGER
			MAX-ACCESS read-only
			STATUS current
			DESCRIPTION
				"Get the CPU health status."
			::= { blade31CPUEntry 5 }
		
		b31CPULocation OBJECT-TYPE
			SYNTAX DisplayString
			MAX-ACCESS read-only
			STATUS current
			DESCRIPTION
				"Get the CPU location."
			::= { blade31CPUEntry 6 }
		
		blade31MemoryTable OBJECT-TYPE
			SYNTAX SEQUENCE OF Blade31MemoryEntry
			MAX-ACCESS not-accessible
			STATUS current
			DESCRIPTION
				"A table containing the list of Blade1 FRU information."
			::= { blade31 2007 }
		
		blade31MemoryEntry OBJECT-TYPE
			SYNTAX Blade31MemoryEntry
			MAX-ACCESS not-accessible
			STATUS current
			DESCRIPTION
				"Information about a particular current FRU."
			INDEX { b31MEMIndex }
			::= { blade31MemoryTable 1 }
		
		Blade31MemoryEntry ::=
			SEQUENCE { 
				b31MEMIndex
					INTEGER,
				b31MEMMark
					DisplayString,
				b31MEMInfo
					DisplayString,
				b31MEMPresent
					INTEGER,
				b31MEMHealth
					INTEGER,
				b31MEMLocation
					DisplayString
			 }

		b31MEMIndex OBJECT-TYPE
			SYNTAX INTEGER
			MAX-ACCESS not-accessible
			STATUS current
			DESCRIPTION
				"MEMORY INDEX"
			::= { blade31MemoryEntry 1 }
		
		b31MEMMark OBJECT-TYPE
			SYNTAX DisplayString
			MAX-ACCESS read-only
			STATUS current
			DESCRIPTION
				"Get the memory silk-screen."
			::= { blade31MemoryEntry 2 }
		
		b31MEMInfo OBJECT-TYPE
			SYNTAX DisplayString
			MAX-ACCESS read-only
			STATUS current
			DESCRIPTION
				"Get the memory description of vendor, frequency and capacity."
			::= { blade31MemoryEntry 3 }
		
		b31MEMPresent OBJECT-TYPE
			SYNTAX INTEGER
			MAX-ACCESS read-only
			STATUS current
			DESCRIPTION
				"Get the memory presence status."
			::= { blade31MemoryEntry 4 }
		
		b31MEMHealth OBJECT-TYPE
			SYNTAX INTEGER
			MAX-ACCESS read-only
			STATUS current
			DESCRIPTION
				"Get the memory health status."
			::= { blade31MemoryEntry 5 }
		
		b31MEMLocation OBJECT-TYPE
			SYNTAX DisplayString
			MAX-ACCESS read-only
			STATUS current
			DESCRIPTION
				"Get the memory location."
			::= { blade31MemoryEntry 6 }
		
		blade31MezzTable OBJECT-TYPE
			SYNTAX SEQUENCE OF Blade31MezzEntry
			MAX-ACCESS not-accessible
			STATUS current
			DESCRIPTION
				"A table containing the list of Blade1 FRU information."
			::= { blade31 2008 }
		
		blade31MezzEntry OBJECT-TYPE
			SYNTAX Blade31MezzEntry
			MAX-ACCESS not-accessible
			STATUS current
			DESCRIPTION
				"Information about a particular current FRU."
			INDEX { b31MezzIndex }
			::= { blade31MezzTable 1 }
		
		Blade31MezzEntry ::=
			SEQUENCE { 
				b31MezzIndex
					INTEGER,
				b31MezzMark
					DisplayString,
				b31MezzInfo
					DisplayString,
				b31MezzPresent
					INTEGER,
				b31MezzHealth
					INTEGER,
				b31MezzLocation
					DisplayString,
				b31MezzMac
					DisplayString
			 }

		b31MezzIndex OBJECT-TYPE
			SYNTAX INTEGER
			MAX-ACCESS not-accessible
			STATUS current
			DESCRIPTION
				"MEZZ INDEX"
			::= { blade31MezzEntry 1 }
		
		b31MezzMark OBJECT-TYPE
			SYNTAX DisplayString
			MAX-ACCESS read-only
			STATUS current
			DESCRIPTION
				"Get the MEZZ silk-screen."
			::= { blade31MezzEntry 2 }
		
		b31MezzInfo OBJECT-TYPE
			SYNTAX DisplayString
			MAX-ACCESS read-only
			STATUS current
			DESCRIPTION
				"Get the MEZZ description of type."
			::= { blade31MezzEntry 3 }
		
		b31MezzPresent OBJECT-TYPE
			SYNTAX INTEGER
			MAX-ACCESS read-only
			STATUS current
			DESCRIPTION
				"Get the MEZZ presence status."
			::= { blade31MezzEntry 4 }
		
		b31MezzHealth OBJECT-TYPE
			SYNTAX INTEGER
			MAX-ACCESS read-only
			STATUS current
			DESCRIPTION
				"Get the MEZZ health status."
			::= { blade31MezzEntry 5 }
		
		b31MezzLocation OBJECT-TYPE
			SYNTAX DisplayString
			MAX-ACCESS read-only
			STATUS current
			DESCRIPTION
				"Get the MEZZ location."
			::= { blade31MezzEntry 6 }
		
		b31MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade31MezzEntry 7 }
		
		blade31DiskTable OBJECT-TYPE
			SYNTAX SEQUENCE OF Blade31DiskEntry
			MAX-ACCESS not-accessible
			STATUS current
			DESCRIPTION
				"A table containing the list of Blade1 FRU information."
			::= { blade31 2009 }
		
		blade31DiskEntry OBJECT-TYPE
			SYNTAX Blade31DiskEntry
			MAX-ACCESS not-accessible
			STATUS current
			DESCRIPTION
				"Information about a particular current FRU."
			INDEX { b31DiskIndex }
			::= { blade31DiskTable 1 }
		
		Blade31DiskEntry ::=
			SEQUENCE { 
				b31DiskIndex
					INTEGER,
				b31DiskMark
					DisplayString,
				b31DiskInfo
					DisplayString,
				b31DiskPresent
					INTEGER,
				b31DiskHealth
					INTEGER,
				b31DiskLocation
					DisplayString
			 }

		b31DiskIndex OBJECT-TYPE
			SYNTAX INTEGER
			MAX-ACCESS not-accessible
			STATUS current
			DESCRIPTION
				"DISK INDEX"
			::= { blade31DiskEntry 1 }
		
		b31DiskMark OBJECT-TYPE
			SYNTAX DisplayString
			MAX-ACCESS read-only
			STATUS current
			DESCRIPTION
				"Get the disk silk-screen."
			::= { blade31DiskEntry 2 }
		
		b31DiskInfo OBJECT-TYPE
			SYNTAX DisplayString
			MAX-ACCESS read-only
			STATUS current
			DESCRIPTION
				"Get the disk description of vendor, capacity and speed."
			::= { blade31DiskEntry 3 }
		
		b31DiskPresent OBJECT-TYPE
			SYNTAX INTEGER
			MAX-ACCESS read-only
			STATUS current
			DESCRIPTION
				"Get the disk presence status."
			::= { blade31DiskEntry 4 }
		
		b31DiskHealth OBJECT-TYPE
			SYNTAX INTEGER
			MAX-ACCESS read-only
			STATUS current
			DESCRIPTION
				"Get the disk health status."
			::= { blade31DiskEntry 5 }
		
		b31DiskLocation OBJECT-TYPE
			SYNTAX DisplayString
			MAX-ACCESS read-only
			STATUS current
			DESCRIPTION
				"Get the disk location."
			::= { blade31DiskEntry 6 }
		
		blade31SecretKvmVmmTable OBJECT-TYPE
			SYNTAX SEQUENCE OF Blade31SecretKvmVmmEntry
			MAX-ACCESS not-accessible
			STATUS current
			DESCRIPTION
				"A table containing the list of Blade31 KVM&VMM secret information."
			::= { blade31 2010 }

		blade31SecretKvmVmmEntry OBJECT-TYPE
			SYNTAX Blade31SecretKvmVmmEntry
			MAX-ACCESS not-accessible
			STATUS current
			DESCRIPTION
				"Information about a particular current KVM&VMM."
			INDEX { b31SecretKvmVmmIndex }
			::= { blade31SecretKvmVmmTable 1 }
		Blade31SecretKvmVmmEntry ::=
			SEQUENCE { 
				b31SecretKvmVmmIndex
					INTEGER,
				b31SecretKvmState
					INTEGER,
				b31SecretVmmState
					INTEGER,
				b31MMSecretVmmKey
					DisplayString,
				b31SecretVmmKey
					DisplayString
			 }
		b31SecretKvmVmmIndex OBJECT-TYPE
			SYNTAX INTEGER
			MAX-ACCESS not-accessible
			STATUS current
			DESCRIPTION
				"KVM&VMM INDEX."
			::= { blade31SecretKvmVmmEntry 1 }
		b31SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade31SecretKvmVmmEntry 2 }
		b31SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade31SecretKvmVmmEntry 3 }
		b31MMSecretVmmKey OBJECT-TYPE
			SYNTAX DisplayString
			MAX-ACCESS read-only
			STATUS current
			DESCRIPTION
				"Get the MM secret VMM key."
			::= { blade31SecretKvmVmmEntry 4 }
		b31SecretVmmKey OBJECT-TYPE
			SYNTAX DisplayString
			MAX-ACCESS read-write
			STATUS current
			DESCRIPTION
				"Set the secret VMM key."
			::= { blade31SecretKvmVmmEntry 5 }
		blade32 OBJECT IDENTIFIER ::= { blades 32 }

		
 		b32DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { blade32 4 }
		
 		b32PowerState OBJECT-TYPE
			SYNTAX DisplayString
			MAX-ACCESS read-write
			STATUS current
			DESCRIPTION
				"The power state of a blade.  This is used to find out 
				if a blade is present, healthy, on/off or to shutdown and turn on 
				a blade.   
				poweron - Power on a blade
				poweroff - Power off a blade"
			::= { blade32 5 }
		
 		b32Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { blade32 6 }

		
 		b32Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"b12Health information about a particular b12Location. 
				This will be one of the following:
				(0-ok, 1-minor, 2-major, 3-majorandminor,4-critical,5-criticalandminor,6-criticalandmajor,7-criticalandmajorandminor)"
			::= { blade32 8 }
		
 		b32HealthEvents OBJECT-TYPE
			SYNTAX DisplayString
			MAX-ACCESS read-only
			STATUS current
			DESCRIPTION
				"Events that contribute to the b12Health of the b12Location.  
				This is a list of events currently happening on the 
				b12Location."
			::= { blade32 9 }
		
 		b32ClearSEL OBJECT-TYPE
			SYNTAX INTEGER { clear(1) }
			MAX-ACCESS read-write
			STATUS current
			DESCRIPTION
				"Clean the BMC's SEL on the board."
			::= { blade32 12 }
		
 		b32ExDiskBoardPresence OBJECT-TYPE
			SYNTAX INTEGER
				{
				not-present(0),
				present(1)
				}
			MAX-ACCESS read-only
			STATUS current
			DESCRIPTION
				"Used to find out if the extended disk board is present.
				0 - not present
				1 - present"
			::= { blade32 14 }
		
 		b32BladeVersion OBJECT-TYPE
			SYNTAX DisplayString
			MAX-ACCESS read-only
			STATUS current
			DESCRIPTION
				"display the Version of board12."
			::= { blade32 20 }
		
 		b32MACAddress OBJECT-TYPE
			SYNTAX DisplayString
			MAX-ACCESS read-only
			STATUS current
			DESCRIPTION
				"display the MACAddress of board12."
			::= { blade32 21 }
		
				
							
		
 		b32Safepwofftime OBJECT-TYPE
			SYNTAX INTEGER
			MAX-ACCESS read-write
			STATUS current
			DESCRIPTION
				"the safe poweroff time.
				"
			::= { blade32 26 }
		
 		b32BiosBootOption OBJECT-TYPE
			SYNTAX DisplayString
			MAX-ACCESS read-write
			STATUS current
			DESCRIPTION
				"Get/Set the board Bios Boot Option.
				Get return: 
					disable
					once/persistent,<boot option>
				
				<boot option>:
					No override                                              
					Force PXE                                                
					Force boot from default Hard-drive[2]                    
					Force boot from default Hard-drive, request Safe Mode[2] 
				Force boot from default Diagnostic Partition[2]          
				Force boot from default CD/DVD[2]           
				Force boot into BIOS Setup
				Force boot from Floppy/primary removable media           
				
				Set format:
				   disable
				   once/persistent,<boot set option>
				   
				   <boot set option>:
				   0=No override                                              
					1=Force PXE                                                
					2=Force boot from default Hard-drive[2]                    
					3=Force boot from default Hard-drive, request Safe Mode[2] 
				4=Force boot from default Diagnostic Partition[2]          
				5=Force boot from default CD/DVD[2]                        
				6=Force boot into BIOS Setup
				15=Force boot from Floppy/primary removable media           
				
				"
			::= { blade32 32 }
		
 		b32Systeminfo OBJECT-TYPE
			SYNTAX DisplayString
			MAX-ACCESS read-write
			STATUS current
			DESCRIPTION
				"display the system information of board12."
			::= { blade32 36 }

		
 		b32SystemProperties OBJECT-TYPE
			SYNTAX DisplayString
			MAX-ACCESS read-only
			STATUS current
			DESCRIPTION
				"Get the power of blade1."
			::= { blade32 39 }
		
 		b32BiosCfg OBJECT-TYPE
			SYNTAX DisplayString
			MAX-ACCESS read-write
			STATUS current
			DESCRIPTION
				"Get the power of blade1."
			::= { blade32 40 }
		
 		b32WDTBootEnable OBJECT-TYPE
			SYNTAX INTEGER
				{
				disabled(0),
				enabled(1)
				}
			MAX-ACCESS read-only
			STATUS current
			DESCRIPTION
				"Used to find out whether timer is enabled.
				0 - Disabled
				1 - Enabled
				"
			::= { blade32 41 }
		
 		b32RealTimePower OBJECT-TYPE
			SYNTAX INTEGER
			MAX-ACCESS read-only
			STATUS current
			DESCRIPTION
				" "
			::= { blade32 43 }
		
 		b32PowerCapping OBJECT-TYPE
			SYNTAX DisplayString
			MAX-ACCESS read-write
			STATUS current
			DESCRIPTION
				" "
			::= { blade32 44 }
		
 		b32Powerreference OBJECT-TYPE
			SYNTAX INTEGER
			MAX-ACCESS read-only
			STATUS current
			DESCRIPTION
				" "
			::= { blade32 45 }
		
 		b32ClearBiosConfig OBJECT-TYPE
			SYNTAX INTEGER
			MAX-ACCESS read-write
			STATUS current
			DESCRIPTION
				" "
			::= { blade32 46 }
		
 		b32BmcIP OBJECT-TYPE
			SYNTAX DisplayString
			MAX-ACCESS read-write
			STATUS current
			DESCRIPTION
				"Used to get or set the BMC straight IP address or ARM IP
				settable format:
				[bmc|bond0|eth0|eth2],Ipaddress,Mask,Gateway"
			::= { blade32 47 }
		
 		b32BmcUserAdd OBJECT-TYPE
			SYNTAX DisplayString
			MAX-ACCESS read-write
			STATUS current
			DESCRIPTION
				"Used to Add the BMC User
				settable format:
				username,passwd"
			::= { blade32 48 }
		
 		b32BmcUserDel OBJECT-TYPE
			SYNTAX DisplayString
			MAX-ACCESS read-write
			STATUS current
			DESCRIPTION
				"Used to Del the BMC User
				settable format:
				username"
			::= { blade32 49 }
		
 		b32BmcUserPasswd OBJECT-TYPE
			SYNTAX DisplayString
			MAX-ACCESS read-write
			STATUS current
			DESCRIPTION
				"Used to Change the BMC User Passwd
				settable format:
				username,passwd"
			::= { blade32 50 }
		
 		b32BmcUserpropertychg OBJECT-TYPE
			SYNTAX DisplayString
			MAX-ACCESS read-write
			STATUS current
			DESCRIPTION
				"Used to Change the BMC User Property
				settable format:
				username,property"
			::= { blade32 51 }
		
 		b32BmcGateway OBJECT-TYPE
			SYNTAX DisplayString
			MAX-ACCESS read-write
			STATUS current
			DESCRIPTION
				"Read or set the gateway."
			::= { blade32 52 }
		
 		b32SlotBitmap OBJECT-TYPE
			SYNTAX INTEGER
			MAX-ACCESS read-only
			STATUS current
			DESCRIPTION
				" "
			::= { blade32 55 }
		
		b32systemGuid OBJECT-TYPE
			SYNTAX DisplayString
			MAX-ACCESS read-only
			STATUS current
			DESCRIPTION
				" "
			::= { blade32 56 }
		
		b32ProductName OBJECT-TYPE
			SYNTAX DisplayString
			MAX-ACCESS read-only
			STATUS current
			DESCRIPTION
				"display the Version of board12."
			::= { blade32 57 }
			
		b32BundleVersion OBJECT-TYPE
			SYNTAX DisplayString
			MAX-ACCESS read-write
			STATUS current
			DESCRIPTION
				"Get or set the board32 bundle version."
			::= { blade32 58 }

 		blade32SensorTargetTable OBJECT-TYPE
			SYNTAX SEQUENCE OF Blade32SensorTargetEntry
			MAX-ACCESS not-accessible
			STATUS current
			DESCRIPTION
				"A table containing the list of sensor information."
			::= { blade32 2001 }
		
 		blade32SensorTargetEntry OBJECT-TYPE
			SYNTAX Blade32SensorTargetEntry
			MAX-ACCESS not-accessible
			STATUS current
			DESCRIPTION
				"Information about a particular current sensor."
			INDEX { b12Target }
			::= { blade32SensorTargetTable 1 }
		
		Blade32SensorTargetEntry ::=
			SEQUENCE { 
				b32Target
					DisplayString,
				b32Current
					DisplayString,
				b32ThresholdsAll
					DisplayString,
				b32UpperCritical
					DisplayString,
				b32UpperNonCritical
					DisplayString,
				b32UpperNonRecoverable
					DisplayString,
				b32LowerNonCritical
					DisplayString,
				b32LowerCritical
					DisplayString,
				b32LowerNonRecoverable
					DisplayString,
				b32SensorHealth
					INTEGER,
				b32SensorHealthEvents
					DisplayString,
				b32NegativeHysteresis
					DisplayString,
				b32PositiveHysteresis
					DisplayString,
				b32SensorType
					DisplayString,
				b32SensorFRUInfo
					DisplayString
			 }

 		b32Target OBJECT-TYPE
			SYNTAX DisplayString
			MAX-ACCESS not-accessible
			STATUS current
			DESCRIPTION
				"sensor Name"
			::= { blade32SensorTargetEntry 1 }
		
 		b32Current OBJECT-TYPE
			SYNTAX DisplayString
			MAX-ACCESS read-only
			STATUS current
			DESCRIPTION
				"Display the current value of a sensor."
			::= { blade32SensorTargetEntry 2 }
		
 		b32ThresholdsAll OBJECT-TYPE
			SYNTAX DisplayString
			MAX-ACCESS read-only
			STATUS current
			DESCRIPTION
				"All thresholds of a sensor"
			::= { blade32SensorTargetEntry 3 }
		
 		b32UpperCritical OBJECT-TYPE
			SYNTAX DisplayString
			MAX-ACCESS read-write
			STATUS current
			DESCRIPTION
				"Upper critical thresholds"
			::= { blade32SensorTargetEntry 4 }
		
 		b32UpperNonCritical OBJECT-TYPE
			SYNTAX DisplayString
			MAX-ACCESS read-write
			STATUS current
			DESCRIPTION
				"Upper non-critical thresholds"
			::= { blade32SensorTargetEntry 5 }
		
 		b32UpperNonRecoverable OBJECT-TYPE
			SYNTAX DisplayString
			MAX-ACCESS read-write
			STATUS current
			DESCRIPTION
				"Upper non-recoverable thresholds"
			::= { blade32SensorTargetEntry 6 }
		
 		b32LowerNonCritical OBJECT-TYPE
			SYNTAX DisplayString
			MAX-ACCESS read-write
			STATUS current
			DESCRIPTION
				"Lower non-critical thresholds"
			::= { blade32SensorTargetEntry 7 }
		
 		b32LowerCritical OBJECT-TYPE
			SYNTAX DisplayString
			MAX-ACCESS read-write
			STATUS current
			DESCRIPTION
				"Lower critical thresholds"
			::= { blade32SensorTargetEntry 8 }
		
 		b32LowerNonRecoverable OBJECT-TYPE
			SYNTAX DisplayString
			MAX-ACCESS read-write
			STATUS current
			DESCRIPTION
				"Lower non-recoverable thresholds"
			::= { blade32SensorTargetEntry 9 }
		
 		b32SensorHealth OBJECT-TYPE
			SYNTAX INTEGER
				{
				ok(0),
				minor(1),
				major(2),
				critical(3)
				}
			MAX-ACCESS read-only
			STATUS current
			DESCRIPTION
				"b12Health information about a particular b12Location. 
				This will be one of the following:
				(0-ok, 1-minor, 2-major, 3-critical)"
			::= { blade32SensorTargetEntry 10 }
		
 		b32SensorHealthEvents OBJECT-TYPE
			SYNTAX DisplayString
			MAX-ACCESS read-only
			STATUS current
			DESCRIPTION
				"Events that contribute to the b12Health of the b12Location.  
				This is a list of events currently happening on the 
				b12Location."
			::= { blade32SensorTargetEntry 11 }
		
		
 		b32NegativeHysteresis OBJECT-TYPE
			SYNTAX DisplayString
			MAX-ACCESS read-write
			STATUS current
			DESCRIPTION
				"Get/Set the negativeHysteresis value"
			::= { blade32SensorTargetEntry 16 }
		
 		b32PositiveHysteresis OBJECT-TYPE
			SYNTAX DisplayString
			MAX-ACCESS read-write
			STATUS current
			DESCRIPTION
				"Get/Set the positiveHysteresis value."
			::= { blade32SensorTargetEntry 17 }
		
 		b32SensorType OBJECT-TYPE
			SYNTAX DisplayString
			MAX-ACCESS read-only
			STATUS current
			DESCRIPTION
				"Get the type of the sensor."
			::= { blade32SensorTargetEntry 18 }
		
 		b32SensorFRUInfo OBJECT-TYPE
			SYNTAX DisplayString
			MAX-ACCESS read-only
			STATUS current
			DESCRIPTION
				"Get the fruinfo of the sensor."
			::= { blade32SensorTargetEntry 19 }
		
 		blade32FruTable OBJECT-TYPE
			SYNTAX SEQUENCE OF Blade32FruEntry
			MAX-ACCESS not-accessible
			STATUS current
			DESCRIPTION
				"A table containing the list of FRU information."
			::= { blade32 2002 }
		
 		blade32FruEntry OBJECT-TYPE
			SYNTAX Blade32FruEntry
			MAX-ACCESS not-accessible
			STATUS current
			DESCRIPTION
				"Information about a particular current FRU."
			INDEX { b12fruNumber }
			::= { blade32FruTable 1 }
		
		Blade32FruEntry ::=
			SEQUENCE { 
				b32fruNumber
					INTEGER,
				b32FruHotSwapState
					DisplayString,
				b32FruLedProperties
					DisplayString,
				b32FRUControl
					INTEGER,
				b32FRULabel
					DisplayString,
				b32ResetReason
					DisplayString
			 }

 		b32fruNumber OBJECT-TYPE
			SYNTAX INTEGER
			MAX-ACCESS not-accessible
			STATUS current
			DESCRIPTION
				" "
			::= { blade32FruEntry 1 }
		
 		b32FruHotSwapState OBJECT-TYPE
			SYNTAX DisplayString
			MAX-ACCESS read-only
			STATUS current
			DESCRIPTION
				"Retrieve the hot swap state of the FRU from the 
				internally known hot swap states of blade12."
			::= { blade32FruEntry 3 }
		
 		b32FruLedProperties OBJECT-TYPE
			SYNTAX DisplayString
			MAX-ACCESS read-only
			STATUS current
			DESCRIPTION
				"Retrieves the LED support information from a FRU. Returns a comma separated
				list of LEDS and the number of FRU supported user LEDs."
			::= { blade32FruEntry 4 }

		

		b32FRUControl OBJECT-TYPE
			SYNTAX INTEGER
			MAX-ACCESS read-write
			STATUS current
			DESCRIPTION
				"Set the FRU to do things like Reset, Power Off Then On, etc.
				Settable value:
				'0' - reset
				'2' - power off then on
				'3' - interrupt control"
			::= { blade32FruEntry 9 }
		
 		b32FRULabel OBJECT-TYPE
			SYNTAX DisplayString
			MAX-ACCESS read-only
			STATUS current
			DESCRIPTION
				"Get fru label of blade12."
			::= { blade32FruEntry 10 }
		
 		b32ResetReason OBJECT-TYPE
			SYNTAX DisplayString
			MAX-ACCESS read-only
			STATUS current
			DESCRIPTION
				"Delete fru label of smm."
			::= { blade32FruEntry 11 }
		
 		blade32FruLedTable OBJECT-TYPE
			SYNTAX SEQUENCE OF Blade32FruLedEntry
			MAX-ACCESS not-accessible
			STATUS current
			DESCRIPTION
				"A table containing the list of led information."
			::= { blade32 2003 }
		
 		blade32FruLedEntry OBJECT-TYPE
			SYNTAX Blade32FruLedEntry
			MAX-ACCESS not-accessible
			STATUS current
			DESCRIPTION
				"Information about a particular current led."
			INDEX { b12FruID, b12FruLed }
			::= { blade32FruLedTable 1 }
		
		Blade32FruLedEntry ::=
			SEQUENCE { 
				b32FruID
					INTEGER,
				b32FruLed
					DisplayString,
				b32FruLedColorProps
					DisplayString,
				b32FruLedState
					DisplayString
			 }

 		b32FruID OBJECT-TYPE
			SYNTAX INTEGER
			MAX-ACCESS not-accessible
			STATUS current
			DESCRIPTION
				" "
			::= { blade32FruLedEntry 1 }
		
 		b32FruLed OBJECT-TYPE
			SYNTAX DisplayString
			MAX-ACCESS not-accessible
			STATUS current
			DESCRIPTION
				" "
			::= { blade32FruLedEntry 2 }
		
 		b32FruLedColorProps OBJECT-TYPE
			SYNTAX DisplayString
			MAX-ACCESS read-only
			STATUS current
			DESCRIPTION
				"Finds out what colors are supported by the LED"
			::= { blade32FruLedEntry 3 }
		
 		b32FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { blade32FruLedEntry 4 }
		
 		blade32FruDescriptionTable OBJECT-TYPE
			SYNTAX SEQUENCE OF Blade32FruDescriptionEntry
			MAX-ACCESS not-accessible
			STATUS current
			DESCRIPTION
				"A table containing the list of blade12 FRU information."
			::= { blade32 2004 }
		
 		blade32FruDescriptionEntry OBJECT-TYPE
			SYNTAX Blade32FruDescriptionEntry
			MAX-ACCESS not-accessible
			STATUS current
			DESCRIPTION
				"Information about a particular current FRU."
			INDEX { b12fruNum }
			::= { blade32FruDescriptionTable 1 }
		
		Blade32FruDescriptionEntry ::=
			SEQUENCE { 
				b32fruNum
					INTEGER,
				b32fruBoardDescription
					DisplayString,
				b32fruBoardManufacturer
					DisplayString,
				b32fruBoardPartNumber
					DisplayString,
				b32fruBoardSerialNumber
					DisplayString,
				b32fruBoardManufactureDate
					DisplayString,
				b32fruProductDescription
					DisplayString,
				b32fruProductManufacturer
					DisplayString,
				b32fruProductPartNumber
					DisplayString,
				b32fruProductSerialNumber
					DisplayString,
				b32fruProductRevision
					DisplayString,
				b32fruAll
					DisplayString
			 }

 		b32fruNum OBJECT-TYPE
			SYNTAX INTEGER
			MAX-ACCESS not-accessible
			STATUS current
			DESCRIPTION
				"blade12 FRU's INDEX"
			::= { blade32FruDescriptionEntry 1 }
		
 		b32fruBoardDescription OBJECT-TYPE
			SYNTAX DisplayString
			MAX-ACCESS read-only
			STATUS current
			DESCRIPTION
				"Used to read the Board Description from the blade12 fru."
			::= { blade32FruDescriptionEntry 2 }
		
 		b32fruBoardManufacturer OBJECT-TYPE
			SYNTAX DisplayString
			MAX-ACCESS read-only
			STATUS current
			DESCRIPTION
				"Used to read the Board Manufacturer from the bladef12 fru."
			::= { blade32FruDescriptionEntry 3 }
		
 		b32fruBoardPartNumber OBJECT-TYPE
			SYNTAX DisplayString
			MAX-ACCESS read-only
			STATUS current
			DESCRIPTION
				"Used to read the Board Part Number from the blade12 fru."
			::= { blade32FruDescriptionEntry 4 }
		
 		b32fruBoardSerialNumber OBJECT-TYPE
			SYNTAX DisplayString
			MAX-ACCESS read-only
			STATUS current
			DESCRIPTION
				"Used to read the Board Serial Number from the blade12 fru."
			::= { blade32FruDescriptionEntry 5 }
		
 		b32fruBoardManufactureDate OBJECT-TYPE
			SYNTAX DisplayString
			MAX-ACCESS read-only
			STATUS current
			DESCRIPTION
				"Used to read the Board Manufacture Date from the blade12 fru."
			::= { blade32FruDescriptionEntry 6 }
		
 		b32fruProductDescription OBJECT-TYPE
			SYNTAX DisplayString
			MAX-ACCESS read-only
			STATUS current
			DESCRIPTION
				"Used to read the Product Description from the blade12 fru."
			::= { blade32FruDescriptionEntry 7 }
		
 		b32fruProductManufacturer OBJECT-TYPE
			SYNTAX DisplayString
			MAX-ACCESS read-only
			STATUS current
			DESCRIPTION
				"Used to read the Product Manufacturer from the blade12 fru."
			::= { blade32FruDescriptionEntry 8 }
		
 		b32fruProductPartNumber OBJECT-TYPE
			SYNTAX DisplayString
			MAX-ACCESS read-only
			STATUS current
			DESCRIPTION
				"Used to read the Product Part Number from the blade12 fru."
			::= { blade32FruDescriptionEntry 9 }
		
 		b32fruProductSerialNumber OBJECT-TYPE
			SYNTAX DisplayString
			MAX-ACCESS read-only
			STATUS current
			DESCRIPTION
				"Used to read the Product Serial Number from the blade12 fru."
			::= { blade32FruDescriptionEntry 10 }
		
 		b32fruProductRevision OBJECT-TYPE
			SYNTAX DisplayString
			MAX-ACCESS read-only
			STATUS current
			DESCRIPTION
				"Used to read the Product Revision from the blade12 fru."
			::= { blade32FruDescriptionEntry 13 }
		
 		b32fruAll OBJECT-TYPE
			SYNTAX DisplayString
			MAX-ACCESS read-only
			STATUS current
			DESCRIPTION
				"Used to read the fru info all."
			::= { blade32FruDescriptionEntry 14 }
		
		blade32CPUTable OBJECT-TYPE
			SYNTAX SEQUENCE OF Blade32CPUEntry
			MAX-ACCESS not-accessible
			STATUS current
			DESCRIPTION
				"A table containing the list of Blade1 FRU information."
			::= { blade32 2006 }
		
		blade32CPUEntry OBJECT-TYPE
			SYNTAX Blade32CPUEntry
			MAX-ACCESS not-accessible
			STATUS current
			DESCRIPTION
				"Information about a particular current FRU."
			INDEX { b32CPUIndex }
			::= { blade32CPUTable 1 }
		
		Blade32CPUEntry ::=
			SEQUENCE { 
				b32CPUIndex
					INTEGER,
				b32CPUMark
					DisplayString,
				b32CPUInfo
					DisplayString,
				b32CPUPresent
					INTEGER,
				b32CPUHealth
					INTEGER,
				b32CPULocation
					DisplayString
			 }

		b32CPUIndex OBJECT-TYPE
			SYNTAX INTEGER
			MAX-ACCESS not-accessible
			STATUS current
			DESCRIPTION
				"CPU INDEX"
			::= { blade32CPUEntry 1 }
		
		b32CPUMark OBJECT-TYPE
			SYNTAX DisplayString
			MAX-ACCESS read-only
			STATUS current
			DESCRIPTION
				"Get the CPU silk-screen."
			::= { blade32CPUEntry 2 }
		
		b32CPUInfo OBJECT-TYPE
			SYNTAX DisplayString
			MAX-ACCESS read-only
			STATUS current
			DESCRIPTION
				"Get the CPU description of vendor, type and frequency."
			::= { blade32CPUEntry 3 }
		
		b32CPUPresent OBJECT-TYPE
			SYNTAX INTEGER
			MAX-ACCESS read-only
			STATUS current
			DESCRIPTION
				"Get the CPU presence status."
			::= { blade32CPUEntry 4 }
		
		b32CPUHealth OBJECT-TYPE
			SYNTAX INTEGER
			MAX-ACCESS read-only
			STATUS current
			DESCRIPTION
				"Get the CPU health status."
			::= { blade32CPUEntry 5 }
		
		b32CPULocation OBJECT-TYPE
			SYNTAX DisplayString
			MAX-ACCESS read-only
			STATUS current
			DESCRIPTION
				"Get the CPU location."
			::= { blade32CPUEntry 6 }
		
		blade32MemoryTable OBJECT-TYPE
			SYNTAX SEQUENCE OF Blade32MemoryEntry
			MAX-ACCESS not-accessible
			STATUS current
			DESCRIPTION
				"A table containing the list of Blade1 FRU information."
			::= { blade32 2007 }
		
		blade32MemoryEntry OBJECT-TYPE
			SYNTAX Blade32MemoryEntry
			MAX-ACCESS not-accessible
			STATUS current
			DESCRIPTION
				"Information about a particular current FRU."
			INDEX { b32MEMIndex }
			::= { blade32MemoryTable 1 }
		
		Blade32MemoryEntry ::=
			SEQUENCE { 
				b32MEMIndex
					INTEGER,
				b32MEMMark
					DisplayString,
				b32MEMInfo
					DisplayString,
				b32MEMPresent
					INTEGER,
				b32MEMHealth
					INTEGER,
				b32MEMLocation
					DisplayString
			 }

		b32MEMIndex OBJECT-TYPE
			SYNTAX INTEGER
			MAX-ACCESS not-accessible
			STATUS current
			DESCRIPTION
				"MEMORY INDEX"
			::= { blade32MemoryEntry 1 }
		
		b32MEMMark OBJECT-TYPE
			SYNTAX DisplayString
			MAX-ACCESS read-only
			STATUS current
			DESCRIPTION
				"Get the memory silk-screen."
			::= { blade32MemoryEntry 2 }
		
		b32MEMInfo OBJECT-TYPE
			SYNTAX DisplayString
			MAX-ACCESS read-only
			STATUS current
			DESCRIPTION
				"Get the memory description of vendor, frequency and capacity."
			::= { blade32MemoryEntry 3 }
		
		b32MEMPresent OBJECT-TYPE
			SYNTAX INTEGER
			MAX-ACCESS read-only
			STATUS current
			DESCRIPTION
				"Get the memory presence status."
			::= { blade32MemoryEntry 4 }
		
		b32MEMHealth OBJECT-TYPE
			SYNTAX INTEGER
			MAX-ACCESS read-only
			STATUS current
			DESCRIPTION
				"Get the memory health status."
			::= { blade32MemoryEntry 5 }
		
		b32MEMLocation OBJECT-TYPE
			SYNTAX DisplayString
			MAX-ACCESS read-only
			STATUS current
			DESCRIPTION
				"Get the memory location."
			::= { blade32MemoryEntry 6 }
		
		blade32MezzTable OBJECT-TYPE
			SYNTAX SEQUENCE OF Blade32MezzEntry
			MAX-ACCESS not-accessible
			STATUS current
			DESCRIPTION
				"A table containing the list of Blade1 FRU information."
			::= { blade32 2008 }
		
		blade32MezzEntry OBJECT-TYPE
			SYNTAX Blade32MezzEntry
			MAX-ACCESS not-accessible
			STATUS current
			DESCRIPTION
				"Information about a particular current FRU."
			INDEX { b32MezzIndex }
			::= { blade32MezzTable 1 }
		
		Blade32MezzEntry ::=
			SEQUENCE { 
				b32MezzIndex
					INTEGER,
				b32MezzMark
					DisplayString,
				b32MezzInfo
					DisplayString,
				b32MezzPresent
					INTEGER,
				b32MezzHealth
					INTEGER,
				b32MezzLocation
					DisplayString,
				b32MezzMac
					DisplayString
			 }

		b32MezzIndex OBJECT-TYPE
			SYNTAX INTEGER
			MAX-ACCESS not-accessible
			STATUS current
			DESCRIPTION
				"MEZZ INDEX"
			::= { blade32MezzEntry 1 }
		
		b32MezzMark OBJECT-TYPE
			SYNTAX DisplayString
			MAX-ACCESS read-only
			STATUS current
			DESCRIPTION
				"Get the MEZZ silk-screen."
			::= { blade32MezzEntry 2 }
		
		b32MezzInfo OBJECT-TYPE
			SYNTAX DisplayString
			MAX-ACCESS read-only
			STATUS current
			DESCRIPTION
				"Get the MEZZ description of type."
			::= { blade32MezzEntry 3 }
		
		b32MezzPresent OBJECT-TYPE
			SYNTAX INTEGER
			MAX-ACCESS read-only
			STATUS current
			DESCRIPTION
				"Get the MEZZ presence status."
			::= { blade32MezzEntry 4 }
		
		b32MezzHealth OBJECT-TYPE
			SYNTAX INTEGER
			MAX-ACCESS read-only
			STATUS current
			DESCRIPTION
				"Get the MEZZ health status."
			::= { blade32MezzEntry 5 }
		
		b32MezzLocation OBJECT-TYPE
			SYNTAX DisplayString
			MAX-ACCESS read-only
			STATUS current
			DESCRIPTION
				"Get the MEZZ location."
			::= { blade32MezzEntry 6 }
		
		b32MezzMac OBJECT-TYPE
			SYNTAX DisplayString
			MAX-ACCESS read-only
			STATUS current
			DESCRIPTION
				"Get the MEZZ ports' mac addresses.
				result value:error code;[[Network port type#Network port MAC address;] [Network port type#Network port MAC address;] …]
				Note: The returned value consists of an error code and information about multiple network ports. Information about each network port is separated by a semicolon (;).
				1) Error code: a decimal number. 0 indicates a success, and another value indicates a failure. Typical error codes include:
					193: The board does not support this function.
					1075904512: The NIC is not installed.
					1075904513: NIC properties cannot be read.
					1075904514: NIC properties are incorrect.
				2) Network port type. The value can be 0, 1, or 2. 0 indicates an Ethernet port, 1 indicates an FC port, and 2 indicates an IB port.
				3) Network port MAC address.
					When the network port type is 0 or 2, the value is the MAC address of the network port, and is a string, for example, D4:B1:10:AF:9D:3A.
					When the network port type is 1, the value is the WWPN of an FC port, and is a string, for example, 1000005056C00001.
				Note:
				1) Two blades on the CH140 share one NIC; therefore, the network ports on the NIC will be allocated to both blades.
				2) If a NIC supports multiple PFs, the system displays only the initial MAC address of the NIC instead of the MAC addresses of all network ports for which the PF is enabled.
				"
			::= { blade32MezzEntry 7 }
		
		blade32DiskTable OBJECT-TYPE
			SYNTAX SEQUENCE OF Blade32DiskEntry
			MAX-ACCESS not-accessible
			STATUS current
			DESCRIPTION
				"A table containing the list of Blade1 FRU information."
			::= { blade32 2009 }
		
		blade32DiskEntry OBJECT-TYPE
			SYNTAX Blade32DiskEntry
			MAX-ACCESS not-accessible
			STATUS current
			DESCRIPTION
				"Information about a particular current FRU."
			INDEX { b32DiskIndex }
			::= { blade32DiskTable 1 }
		
		Blade32DiskEntry ::=
			SEQUENCE { 
				b32DiskIndex
					INTEGER,
				b32DiskMark
					DisplayString,
				b32DiskInfo
					DisplayString,
				b32DiskPresent
					INTEGER,
				b32DiskHealth
					INTEGER,
				b32DiskLocation
					DisplayString
			 }

		b32DiskIndex OBJECT-TYPE
			SYNTAX INTEGER
			MAX-ACCESS not-accessible
			STATUS current
			DESCRIPTION
				"DISK INDEX"
			::= { blade32DiskEntry 1 }
		
		b32DiskMark OBJECT-TYPE
			SYNTAX DisplayString
			MAX-ACCESS read-only
			STATUS current
			DESCRIPTION
				"Get the disk silk-screen."
			::= { blade32DiskEntry 2 }
		
		b32DiskInfo OBJECT-TYPE
			SYNTAX DisplayString
			MAX-ACCESS read-only
			STATUS current
			DESCRIPTION
				"Get the disk description of vendor, capacity and speed."
			::= { blade32DiskEntry 3 }
		
		b32DiskPresent OBJECT-TYPE
			SYNTAX INTEGER
			MAX-ACCESS read-only
			STATUS current
			DESCRIPTION
				"Get the disk presence status."
			::= { blade32DiskEntry 4 }
		
		b32DiskHealth OBJECT-TYPE
			SYNTAX INTEGER
			MAX-ACCESS read-only
			STATUS current
			DESCRIPTION
				"Get the disk health status."
			::= { blade32DiskEntry 5 }
		
		b32DiskLocation OBJECT-TYPE
			SYNTAX DisplayString
			MAX-ACCESS read-only
			STATUS current
			DESCRIPTION
				"Get the disk location."
			::= { blade32DiskEntry 6 }
		
		blade32SecretKvmVmmTable OBJECT-TYPE
			SYNTAX SEQUENCE OF Blade32SecretKvmVmmEntry
			MAX-ACCESS not-accessible
			STATUS current
			DESCRIPTION
				"A table containing the list of Blade32 KVM&VMM secret information."
			::= { blade32 2010 }
		blade32SecretKvmVmmEntry OBJECT-TYPE
			SYNTAX Blade32SecretKvmVmmEntry
			MAX-ACCESS not-accessible
			STATUS current
			DESCRIPTION
				"Information about a particular current KVM&VMM."
			INDEX { b32SecretKvmVmmIndex }
			::= { blade32SecretKvmVmmTable 1 }
		Blade32SecretKvmVmmEntry ::=
			SEQUENCE { 
				b32SecretKvmVmmIndex
					INTEGER,
				b32SecretKvmState
					INTEGER,
				b32SecretVmmState
					INTEGER,
				b32MMSecretVmmKey
					DisplayString,
				b32SecretVmmKey
					DisplayString
			 }
		b32SecretKvmVmmIndex OBJECT-TYPE
			SYNTAX INTEGER
			MAX-ACCESS not-accessible
			STATUS current
			DESCRIPTION
				"KVM&VMM INDEX."
			::= { blade32SecretKvmVmmEntry 1 }
		b32SecretKvmState OBJECT-TYPE
			SYNTAX INTEGER
				{
				noEncrypt(1),
				encrypt(2),
				noSupportEncrypt(3),
				noSupportKVM(4)
				}
			MAX-ACCESS read-write
			STATUS current
			DESCRIPTION
				"The KVM secret state."
			::= { blade32SecretKvmVmmEntry 2 }
		b32SecretVmmState OBJECT-TYPE
			SYNTAX INTEGER
				{
				noEncrypt(1),
				encrypt(2),
				noSupportEncrypt(3),
				noSupportVMM(4)
				}
			MAX-ACCESS read-write
			STATUS current
			DESCRIPTION
				"The VMM secret state."
			::= { blade32SecretKvmVmmEntry 3 }
		b32MMSecretVmmKey OBJECT-TYPE
			SYNTAX DisplayString
			MAX-ACCESS read-only
			STATUS current
			DESCRIPTION
				"Get the MM secret VMM key."
			::= { blade32SecretKvmVmmEntry 4 }
		b32SecretVmmKey OBJECT-TYPE
			SYNTAX DisplayString
			MAX-ACCESS read-write
			STATUS current
			DESCRIPTION
				"Set the secret VMM key."
			::= { blade32SecretKvmVmmEntry 5 }
 		fanTray OBJECT IDENTIFIER ::= { hwSMM 5 }
		
 		fanTrayFanTable OBJECT-TYPE
			SYNTAX SEQUENCE OF FanTrayFanEntry
			MAX-ACCESS not-accessible
			STATUS current
			DESCRIPTION
				"A table containing the list of fan information."
			::= { fanTray 2001 }
		
 		fanTrayFanEntry OBJECT-TYPE
			SYNTAX FanTrayFanEntry
			MAX-ACCESS not-accessible
			STATUS current
			DESCRIPTION
				" "
			INDEX { fanIndex }
			::= { fanTrayFanTable 1 }
		
		FanTrayFanEntry ::=
			SEQUENCE { 
				fanIndex
					INTEGER,
				fanPresence
					INTEGER,
				fanSpeed
					DisplayString,
				fanInfo
					DisplayString,
				fanUpdate
					DisplayString,
				fanVersion
					DisplayString,
				fanStatus
					INTEGER
			 }

 		fanIndex OBJECT-TYPE
			SYNTAX INTEGER
			MAX-ACCESS not-accessible
			STATUS current
			DESCRIPTION
				"Fan number index."
			::= { fanTrayFanEntry 1 }
		
 		fanPresence OBJECT-TYPE
			SYNTAX INTEGER
				{
				not-present(0),
				present(1),
				indeterminate(2)
				}
			MAX-ACCESS read-only
			STATUS current
			DESCRIPTION
				"Used to find out if the fan is present in the shelf.
				0 - not present
				1 - present
				2 - indeterminate"
			::= { fanTrayFanEntry 2 }
		
 		fanSpeed OBJECT-TYPE
			SYNTAX DisplayString
			MAX-ACCESS read-write
			STATUS current
			DESCRIPTION
				"Used to get or set the fan's speed.
				Set value: 30~100."
			::= { fanTrayFanEntry 3 }
		
 		fanInfo OBJECT-TYPE
			SYNTAX DisplayString
			MAX-ACCESS read-write
			STATUS current
			DESCRIPTION
				"Used to get or set the fan's electronic label."
			::= { fanTrayFanEntry 4 }
		
 		fanUpdate OBJECT-TYPE
			SYNTAX DisplayString
			MAX-ACCESS read-write
			STATUS current
			DESCRIPTION
				"Used to Send Fan Update Cmd,Get Fan Update Process
				Settable format:
				updatefilename"
			::= { fanTrayFanEntry 5 }
		
		fanVersion OBJECT-TYPE
			SYNTAX DisplayString
			MAX-ACCESS read-only
			STATUS current
			DESCRIPTION
				"Used to get fantray version"
			::= { fanTrayFanEntry 6 }
		
		fanStatus OBJECT-TYPE
			SYNTAX INTEGER
			MAX-ACCESS read-only
			STATUS current
			DESCRIPTION
				"Used to get fantray health status"
			::= { fanTrayFanEntry 7 }
		
 		pems OBJECT IDENTIFIER ::= { hwSMM 6 }
		
 		pemsPowerTable OBJECT-TYPE
			SYNTAX SEQUENCE OF PemsPowerEntry
			MAX-ACCESS not-accessible
			STATUS current
			DESCRIPTION
				"A table containing the list of power information."
			::= { pems 2001 }
		
 		pemsPowerEntry OBJECT-TYPE
			SYNTAX PemsPowerEntry
			MAX-ACCESS not-accessible
			STATUS current
			DESCRIPTION
				" "
			INDEX { powerIndex }
			::= { pemsPowerTable 1 }
		
		PemsPowerEntry ::=
			SEQUENCE { 
				powerIndex
					INTEGER,
				powerPresence
					INTEGER,
				powerState
					INTEGER,
				powerRatingPower
					DisplayString,
				powerMode
					DisplayString,
				powerSwitch
					INTEGER,
				powerInfo
					DisplayString,
				powerRuntimePower
					DisplayString,
				powerFaultReason
					DisplayString
			 }

 		powerIndex OBJECT-TYPE
			SYNTAX INTEGER
			MAX-ACCESS not-accessible
			STATUS current
			DESCRIPTION
				"Power number index."
			::= { pemsPowerEntry 1 }
		
 		powerPresence OBJECT-TYPE
			SYNTAX INTEGER
				{
				not-present(0),
				present(1),
				indeterminate(2)
				}
			MAX-ACCESS read-only
			STATUS current
			DESCRIPTION
				"Used to find out if the power is present in the shelf.
				0 - not present
				1 - present
				2 - indeterminate"
			::= { pemsPowerEntry 2 }
		
 		powerState OBJECT-TYPE
			SYNTAX INTEGER
				{
				normal(0),
				abnormal(1)
				}
			MAX-ACCESS read-only
			STATUS current
			DESCRIPTION
				"Used to get the power's state.
				0 - normal
				1 - abnormal"
			::= { pemsPowerEntry 3 }
		
 		powerRatingPower OBJECT-TYPE
			SYNTAX DisplayString
			MAX-ACCESS read-only
			STATUS current
			DESCRIPTION
				"Used to get the power's rating power."
			::= { pemsPowerEntry 4 }
		
 		powerMode OBJECT-TYPE
			SYNTAX DisplayString
			MAX-ACCESS read-only
			STATUS current
			DESCRIPTION
				"Used to get the mode of the power."
			::= { pemsPowerEntry 5 }
		
 		powerSwitch OBJECT-TYPE
			SYNTAX INTEGER
				{
				close(0),
				open(1)
				}
			MAX-ACCESS read-write
			STATUS current
			DESCRIPTION
				"Used to open or close the power.
				0 - close
				1 - open"
			::= { pemsPowerEntry 6 }
		
 		powerInfo OBJECT-TYPE
			SYNTAX DisplayString
			MAX-ACCESS read-only
			STATUS current
			DESCRIPTION
				"Used to get the power's fru infomation."
			::= { pemsPowerEntry 7 }
		
 		powerRuntimePower OBJECT-TYPE
			SYNTAX DisplayString
			MAX-ACCESS read-only
			STATUS current
			DESCRIPTION
				"Used to get the power's runtime power."
			::= { pemsPowerEntry 8 }
		
		powerFaultReason OBJECT-TYPE
			SYNTAX DisplayString
			MAX-ACCESS read-only
			STATUS current
			DESCRIPTION
				"Used to get the power's fault reason."
			::= { pemsPowerEntry 9 }
 		swi OBJECT IDENTIFIER ::= { hwSMM 7 }
		

		swi1 OBJECT IDENTIFIER ::= { swi 1 }

		
 		swi1DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { swi1 4 }
		
 		swi1Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { swi1 6 }

		
 		swi1Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"swi1Health information about a particular swi1Location. 
				This will be one of the following:
				(0-ok, 1-minor, 2-major, 3-majorandminor,4-critical,5-criticalandminor,6-criticalandmajor,7-criticalandmajorandminor)"
			::= { swi1 8 }
		
 		swi1HealthEvents OBJECT-TYPE
			SYNTAX DisplayString
			MAX-ACCESS read-only
			STATUS current
			DESCRIPTION
				"Events that contribute to the swi1Health of the swi1Location.  
				This is a list of events currently happening on the 
				swi1Location."
			::= { swi1 9 }
		
 		swi1ClearSEL OBJECT-TYPE
			SYNTAX INTEGER { clear(1) }
			MAX-ACCESS read-write
			STATUS current
			DESCRIPTION
				"Clean the BMC's SEL on the board."
			::= { swi1 12 }
		
 		swi1ConfigSupport OBJECT-TYPE
			SYNTAX DisplayString
			MAX-ACCESS read-only
			STATUS current
			DESCRIPTION
				"display the ConfigSupport of swi1."
			::= { swi1 18 }
		
 		swi1ConfigInfo OBJECT-TYPE
			SYNTAX DisplayString
			MAX-ACCESS read-only
			STATUS current
			DESCRIPTION
				"display the ConfigInfo of swi1."
			::= { swi1 19 }
		
 		swi1BladeVersion OBJECT-TYPE
			SYNTAX DisplayString
			MAX-ACCESS read-only
			STATUS current
			DESCRIPTION
				"display the Version of swi1."
			::= { swi1 20 }
		
 		swi1FcPortConn OBJECT-TYPE
			SYNTAX OCTET STRING
			MAX-ACCESS read-write
			STATUS current
			DESCRIPTION
				"Used to describe the connection of fc.
				get
				0:invalid
				1:left
				2:right
				
				set
				portid;portdirect
				(e.g.)
				(1;2)  The fc direction of port_1 is right.
				(255;1)The fc direction of all ports is left."
			::= { swi1 21 }
		
		swi1ProductName OBJECT-TYPE
			SYNTAX DisplayString
			MAX-ACCESS read-only
			STATUS current
			DESCRIPTION
				"display the Version of swi1."
			::= { swi1 22 }
			
		swi1BundleVersion OBJECT-TYPE
			SYNTAX DisplayString
			MAX-ACCESS read-write
			STATUS current
			DESCRIPTION
				"Get or set the swi1 bundle version."
			::= { swi1 23 }

		swi1ClearAlarm OBJECT-TYPE
			SYNTAX DisplayString
			MAX-ACCESS read-write
			STATUS current
			DESCRIPTION
				"Clear alarm"
			::= { swi1 24 }
 		swi1SensorTargetTable OBJECT-TYPE
			SYNTAX SEQUENCE OF Swi1SensorTargetEntry
			MAX-ACCESS not-accessible
			STATUS current
			DESCRIPTION
				"A table containing the list of sensor information."
			::= { swi1 2001 }
		
 		swi1SensorTargetEntry OBJECT-TYPE
			SYNTAX Swi1SensorTargetEntry
			MAX-ACCESS not-accessible
			STATUS current
			DESCRIPTION
				"Information about a particular current sensor."
			INDEX { swi1Target }
			::= { swi1SensorTargetTable 1 }
		
		Swi1SensorTargetEntry ::=
			SEQUENCE { 
				swi1Target
					DisplayString,
				swi1Current
					DisplayString,
				swi1ThresholdsAll
					DisplayString,
				swi1UpperCritical
					DisplayString,
				swi1UpperNonCritical
					DisplayString,
				swi1UpperNonRecoverable
					DisplayString,
				swi1LowerNonCritical
					DisplayString,
				swi1LowerCritical
					DisplayString,
				swi1LowerNonRecoverable
					DisplayString,
				swi1SensorHealth
					INTEGER,
				swi1SensorHealthEvents
					DisplayString,
				swi1NegativeHysteresis
					DisplayString,
				swi1PositiveHysteresis
					DisplayString,
				swi1SensorType
					DisplayString,
				swi1SensorFRUInfo
					DisplayString
			 }

 		swi1Target OBJECT-TYPE
			SYNTAX DisplayString
			MAX-ACCESS not-accessible
			STATUS current
			DESCRIPTION
				"sensor Name"
			::= { swi1SensorTargetEntry 1 }
		
 		swi1Current OBJECT-TYPE
			SYNTAX DisplayString
			MAX-ACCESS read-only
			STATUS current
			DESCRIPTION
				"Display the current value of a sensor."
			::= { swi1SensorTargetEntry 2 }
		
 		swi1ThresholdsAll OBJECT-TYPE
			SYNTAX DisplayString
			MAX-ACCESS read-only
			STATUS current
			DESCRIPTION
				"All thresholds of a sensor"
			::= { swi1SensorTargetEntry 3 }
		
 		swi1UpperCritical OBJECT-TYPE
			SYNTAX DisplayString
			MAX-ACCESS read-write
			STATUS current
			DESCRIPTION
				"Upper critical thresholds"
			::= { swi1SensorTargetEntry 4 }
		
 		swi1UpperNonCritical OBJECT-TYPE
			SYNTAX DisplayString
			MAX-ACCESS read-write
			STATUS current
			DESCRIPTION
				"Upper non-critical thresholds"
			::= { swi1SensorTargetEntry 5 }
		
 		swi1UpperNonRecoverable OBJECT-TYPE
			SYNTAX DisplayString
			MAX-ACCESS read-write
			STATUS current
			DESCRIPTION
				"Upper non-recoverable thresholds"
			::= { swi1SensorTargetEntry 6 }
		
 		swi1LowerNonCritical OBJECT-TYPE
			SYNTAX DisplayString
			MAX-ACCESS read-write
			STATUS current
			DESCRIPTION
				"Lower non-critical thresholds"
			::= { swi1SensorTargetEntry 7 }
		
 		swi1LowerCritical OBJECT-TYPE
			SYNTAX DisplayString
			MAX-ACCESS read-write
			STATUS current
			DESCRIPTION
				"Lower critical thresholds"
			::= { swi1SensorTargetEntry 8 }
		
 		swi1LowerNonRecoverable OBJECT-TYPE
			SYNTAX DisplayString
			MAX-ACCESS read-write
			STATUS current
			DESCRIPTION
				"Lower non-recoverable thresholds"
			::= { swi1SensorTargetEntry 9 }
		
 		swi1SensorHealth OBJECT-TYPE
			SYNTAX INTEGER
				{
				ok(0),
				minor(1),
				major(2),
				critical(3)
				}
			MAX-ACCESS read-only
			STATUS current
			DESCRIPTION
				"swi1Health information about a particular swi1Location. 
				This will be one of the following:
				(0-ok, 1-minor, 2-major, 3-critical)"
			::= { swi1SensorTargetEntry 10 }
		
 		swi1SensorHealthEvents OBJECT-TYPE
			SYNTAX DisplayString
			MAX-ACCESS read-only
			STATUS current
			DESCRIPTION
				"Events that contribute to the swi1Health of the swi1Location.  
				This is a list of events currently happening on the 
				swi1Location."
			::= { swi1SensorTargetEntry 11 }
		
		
 		swi1NegativeHysteresis OBJECT-TYPE
			SYNTAX DisplayString
			MAX-ACCESS read-write
			STATUS current
			DESCRIPTION
				"Get/Set the negativeHysteresis value"
			::= { swi1SensorTargetEntry 16 }
		
 		swi1PositiveHysteresis OBJECT-TYPE
			SYNTAX DisplayString
			MAX-ACCESS read-write
			STATUS current
			DESCRIPTION
				"Get/Set the positiveHysteresis value."
			::= { swi1SensorTargetEntry 17 }
		
 		swi1SensorType OBJECT-TYPE
			SYNTAX DisplayString
			MAX-ACCESS read-only
			STATUS current
			DESCRIPTION
				"Get the type of the sensor."
			::= { swi1SensorTargetEntry 18 }
		
 		swi1SensorFRUInfo OBJECT-TYPE
			SYNTAX DisplayString
			MAX-ACCESS read-only
			STATUS current
			DESCRIPTION
				"Get the fruinfo of the sensor."
			::= { swi1SensorTargetEntry 19 }
		
 		swi1FruTable OBJECT-TYPE
			SYNTAX SEQUENCE OF Swi1FruEntry
			MAX-ACCESS not-accessible
			STATUS current
			DESCRIPTION
				"A table containing the list of FRU information."
			::= { swi1 2002 }
		
 		swi1FruEntry OBJECT-TYPE
			SYNTAX Swi1FruEntry
			MAX-ACCESS not-accessible
			STATUS current
			DESCRIPTION
				"Information about a particular current FRU."
			INDEX { swi1fruNumber }
			::= { swi1FruTable 1 }
		
		Swi1FruEntry ::=
			SEQUENCE { 
				swi1fruNumber
					INTEGER,
				swi1FruHotSwapState
					DisplayString,
				swi1FruLedProperties
					DisplayString,
				swi1FRUControl
					INTEGER,
				swi1FRULabel
					DisplayString,
				swi1ResetReason
					DisplayString,
				swi1PowerState
					DisplayString,
				swi1SWIPControl
					DisplayString,
				swi1Gateway
					DisplayString,
				swi1Route
					DisplayString,
				swi1VLanIfIP
					DisplayString,
				swi1FruVersion
					DisplayString,
				swi1SaveConfig
					INTEGER,
				swi1StackState
					INTEGER
			 }

 		swi1fruNumber OBJECT-TYPE
			SYNTAX INTEGER
			MAX-ACCESS not-accessible
			STATUS current
			DESCRIPTION
				"Fru number"
			::= { swi1FruEntry 1 }
		
 		swi1FruHotSwapState OBJECT-TYPE
			SYNTAX DisplayString
			MAX-ACCESS read-only
			STATUS current
			DESCRIPTION
				"Retrieve the hot swap state of the FRU from the 
				internally known hot swap states of swi1."
			::= { swi1FruEntry 3 }
		
 		swi1FruLedProperties OBJECT-TYPE
			SYNTAX DisplayString
			MAX-ACCESS read-only
			STATUS current
			DESCRIPTION
				"Retrieves the LED support information from a FRU. Returns a comma separated
				list of LEDS and the number of FRU supported user LEDs."
			::= { swi1FruEntry 4 }

		

		swi1FRUControl OBJECT-TYPE
			SYNTAX INTEGER
			MAX-ACCESS read-write
			STATUS current
			DESCRIPTION
				"Set the FRU to do things like Reset, Warm Reset, etc.
				Settable value:
				'0' - reset
				'1' - warm reset"
			::= { swi1FruEntry 9 }
		
 		swi1FRULabel OBJECT-TYPE
			SYNTAX DisplayString
			MAX-ACCESS read-only
			STATUS current
			DESCRIPTION
				"Get fru label of swi1."
			::= { swi1FruEntry 10 }
		
 		swi1ResetReason OBJECT-TYPE
			SYNTAX DisplayString
			MAX-ACCESS read-only
			STATUS current
			DESCRIPTION
				"Used to get the FRU reset cause."
			::= { swi1FruEntry 11 }
		
 		swi1PowerState OBJECT-TYPE
			SYNTAX DisplayString
			MAX-ACCESS read-write
			STATUS current
			DESCRIPTION
				"The power state of a switch module. This is used to find out 
				if a switch module is present, healthy, on/off or to shutdown and turn on 
				a switch module.   
				poweron - Power on a switch module
				poweroff - Power off a switch module"
			::= { swi1FruEntry 12 }
		
 		swi1SWIPControl OBJECT-TYPE
			SYNTAX DisplayString
			MAX-ACCESS read-write
			STATUS current
			DESCRIPTION
				"Used to get or set the base IP or fabric IP address of switch module"
			::= { swi1FruEntry 13 }
		
 		swi1Gateway OBJECT-TYPE
			SYNTAX DisplayString
			MAX-ACCESS read-write
			STATUS current
			DESCRIPTION
				"Read or set the gateway."
			::= { swi1FruEntry 14 }
		
 		swi1Route OBJECT-TYPE
			SYNTAX DisplayString
			MAX-ACCESS read-write
			STATUS current
			DESCRIPTION
				"Read or set the route."
			::= { swi1FruEntry 15 }
		
 		swi1VLanIfIP OBJECT-TYPE
			SYNTAX DisplayString
			MAX-ACCESS read-write
			STATUS current
			DESCRIPTION
				"Read or set vlanif1 IP"
			::= { swi1FruEntry 16 }
		
 		swi1FruVersion OBJECT-TYPE
			SYNTAX DisplayString
			MAX-ACCESS read-only
			STATUS current
			DESCRIPTION
				"Used to get the FRU version of the switch module."
			::= { swi1FruEntry 17 }
		
                swi1SaveConfig OBJECT-TYPE
			SYNTAX INTEGER
			MAX-ACCESS read-write
			STATUS current
			DESCRIPTION
				"Save all configurations in swi plane"
			::= { swi1FruEntry 18 }
		
		swi1StackState OBJECT-TYPE
			SYNTAX INTEGER
			MAX-ACCESS read-only
			STATUS current
			DESCRIPTION
				"Get the stack state of switch modules:
				1 -- master switch in a stack
				2 -- standby switch in a stack
				3 -- slave switch in a stack
				4 -- unstacked switch"
			::= { swi1FruEntry 19 }
		
		swi1FruLedTable OBJECT-TYPE
			SYNTAX SEQUENCE OF Swi1FruLedEntry
			MAX-ACCESS not-accessible
			STATUS current
			DESCRIPTION
				"A table containing the list of led information."
			::= { swi1 2003 }
		
 		swi1FruLedEntry OBJECT-TYPE
			SYNTAX Swi1FruLedEntry
			MAX-ACCESS not-accessible
			STATUS current
			DESCRIPTION
				"Information about a particular current led."
			INDEX { swi1FruID, swi1FruLed }
			::= { swi1FruLedTable 1 }
		
		Swi1FruLedEntry ::=
			SEQUENCE { 
				swi1FruID
					INTEGER,
				swi1FruLed
					DisplayString,
				swi1FruLedColorProps
					DisplayString,
				swi1FruLedState
					DisplayString
			 }

 		swi1FruID OBJECT-TYPE
			SYNTAX INTEGER
			MAX-ACCESS not-accessible
			STATUS current
			DESCRIPTION
				"Fru ID"
			::= { swi1FruLedEntry 1 }
		
 		swi1FruLed OBJECT-TYPE
			SYNTAX DisplayString
			MAX-ACCESS not-accessible
			STATUS current
			DESCRIPTION
				"The current FRU indicator name."
			::= { swi1FruLedEntry 2 }
		
 		swi1FruLedColorProps OBJECT-TYPE
			SYNTAX DisplayString
			MAX-ACCESS read-only
			STATUS current
			DESCRIPTION
				"Finds out what colors are supported by the LED"
			::= { swi1FruLedEntry 3 }
		
 		swi1FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { swi1FruLedEntry 4 }
		
 		swi1FruDescriptionTable OBJECT-TYPE
			SYNTAX SEQUENCE OF Swi1FruDescriptionEntry
			MAX-ACCESS not-accessible
			STATUS current
			DESCRIPTION
				"A table containing the list of swi1 FRU information."
			::= { swi1 2004 }
		
 		swi1FruDescriptionEntry OBJECT-TYPE
			SYNTAX Swi1FruDescriptionEntry
			MAX-ACCESS not-accessible
			STATUS current
			DESCRIPTION
				"Information about a particular current FRU."
			INDEX { swi1fruNum }
			::= { swi1FruDescriptionTable 1 }
		
		Swi1FruDescriptionEntry ::=
			SEQUENCE { 
				swi1fruNum
					INTEGER,
				swi1fruBoardDescription
					DisplayString,
				swi1fruBoardManufacturer
					DisplayString,
				swi1fruBoardPartNumber
					DisplayString,
				swi1fruBoardSerialNumber
					DisplayString,
				swi1fruBoardManufactureDate
					DisplayString,
				swi1fruProductDescription
					DisplayString,
				swi1fruProductManufacturer
					DisplayString,
				swi1fruProductPartNumber
					DisplayString,
				swi1fruProductSerialNumber
					DisplayString,
				swi1fruProductRevision
					DisplayString,
				swi1fruAll
					DisplayString
			 }

 		swi1fruNum OBJECT-TYPE
			SYNTAX INTEGER
			MAX-ACCESS not-accessible
			STATUS current
			DESCRIPTION
				"swu1 FRU's INDEX"
			::= { swi1FruDescriptionEntry 1 }
		
 		swi1fruBoardDescription OBJECT-TYPE
			SYNTAX DisplayString
			MAX-ACCESS read-only
			STATUS current
			DESCRIPTION
				"Used to read the Board Description from the swi1 fru."
			::= { swi1FruDescriptionEntry 2 }
		
 		swi1fruBoardManufacturer OBJECT-TYPE
			SYNTAX DisplayString
			MAX-ACCESS read-only
			STATUS current
			DESCRIPTION
				"Used to read the Board Manufacturer from the swi1 fru."
			::= { swi1FruDescriptionEntry 3 }
		
 		swi1fruBoardPartNumber OBJECT-TYPE
			SYNTAX DisplayString
			MAX-ACCESS read-only
			STATUS current
			DESCRIPTION
				"Used to read the Board Part Number from the swi1 fru."
			::= { swi1FruDescriptionEntry 4 }
		
 		swi1fruBoardSerialNumber OBJECT-TYPE
			SYNTAX DisplayString
			MAX-ACCESS read-only
			STATUS current
			DESCRIPTION
				"Used to read the Board Serial Number from the swi1 fru."
			::= { swi1FruDescriptionEntry 5 }
		
 		swi1fruBoardManufactureDate OBJECT-TYPE
			SYNTAX DisplayString
			MAX-ACCESS read-only
			STATUS current
			DESCRIPTION
				"Used to read the Board Manufacture Date from the swi1 fru."
			::= { swi1FruDescriptionEntry 6 }
		
 		swi1fruProductDescription OBJECT-TYPE
			SYNTAX DisplayString
			MAX-ACCESS read-only
			STATUS current
			DESCRIPTION
				"Used to read the Product Description from the swi1 fru."
			::= { swi1FruDescriptionEntry 7 }
		
 		swi1fruProductManufacturer OBJECT-TYPE
			SYNTAX DisplayString
			MAX-ACCESS read-only
			STATUS current
			DESCRIPTION
				"Used to read the Product Manufacturer from the swi1 fru."
			::= { swi1FruDescriptionEntry 8 }
		
 		swi1fruProductPartNumber OBJECT-TYPE
			SYNTAX DisplayString
			MAX-ACCESS read-only
			STATUS current
			DESCRIPTION
				"Used to read the Product Part Number from the swi1 fru."
			::= { swi1FruDescriptionEntry 9 }
		
 		swi1fruProductSerialNumber OBJECT-TYPE
			SYNTAX DisplayString
			MAX-ACCESS read-only
			STATUS current
			DESCRIPTION
				"Used to read the Product Serial Number from the swi1 fru."
			::= { swi1FruDescriptionEntry 10 }
		
 		swi1fruProductRevision OBJECT-TYPE
			SYNTAX DisplayString
			MAX-ACCESS read-only
			STATUS current
			DESCRIPTION
				"Used to read the Product Revision from the swi1 fru."
			::= { swi1FruDescriptionEntry 13 }
		
 		swi1fruAll OBJECT-TYPE
			SYNTAX DisplayString
			MAX-ACCESS read-only
			STATUS current
			DESCRIPTION
				"Used to read the fru info all."
			::= { swi1FruDescriptionEntry 14 }
		
 		swi1PortTargetTable OBJECT-TYPE
			SYNTAX SEQUENCE OF Swi1PortTargetEntry
			MAX-ACCESS not-accessible
			STATUS current
			DESCRIPTION
				"A table containing the list of sensor information."
			::= { swi1 2005 }
		
 		swi1PortTargetEntry OBJECT-TYPE
			SYNTAX Swi1PortTargetEntry
			MAX-ACCESS not-accessible
			STATUS current
			DESCRIPTION
				"Information about a particular current sensor."
			INDEX { swi1PortNum }
			::= { swi1PortTargetTable 1 }
		
		Swi1PortTargetEntry ::=
			SEQUENCE { 
				swi1PortNum
					INTEGER,
				swi1OTMState
					INTEGER,
				swi1OTMInfo
					DisplayString,
				swi1PhyState
					INTEGER,
				swi1PhyReset
					INTEGER,
				swi1PortToBladeSlot
					INTEGER,
				swi1PortName
					DisplayString,
				swi1OTMData
					DisplayString,
			        swi1PortState
					INTEGER		
			 }

 		swi1PortNum OBJECT-TYPE
			SYNTAX INTEGER
			MAX-ACCESS read-only
			STATUS current
			DESCRIPTION
				"Port Num"
			::= { swi1PortTargetEntry 1 }
		
 		swi1OTMState OBJECT-TYPE
			SYNTAX INTEGER
				{
				not-present(0),
				present(1)
				}
			MAX-ACCESS read-only
			STATUS current
			DESCRIPTION
				"Used to get the optical module status. 
				This will be one of the following:
				(0-not present, 1-present)"
			::= { swi1PortTargetEntry 2 }
		
 		swi1OTMInfo OBJECT-TYPE
			SYNTAX DisplayString
			MAX-ACCESS read-only
			STATUS current
			DESCRIPTION
				"Used to get the optical module information."
			::= { swi1PortTargetEntry 3 }
		
 		swi1PhyState OBJECT-TYPE
			SYNTAX INTEGER
				{
				down(0),
				up(1)
				}
			MAX-ACCESS read-only
			STATUS current
			DESCRIPTION
				"Phy state"
			::= { swi1PortTargetEntry 4 }
		
 		swi1PhyReset OBJECT-TYPE
			SYNTAX INTEGER
			MAX-ACCESS write-only
			STATUS current
			DESCRIPTION
				"Phy reset"
			::= { swi1PortTargetEntry 5 }
		
 		swi1PortToBladeSlot OBJECT-TYPE
			SYNTAX INTEGER
			MAX-ACCESS read-only
			STATUS current
			DESCRIPTION
				"Used to get the server slot number."
			::= { swi1PortTargetEntry 6 }
		
 		swi1PortName OBJECT-TYPE
			SYNTAX DisplayString
			MAX-ACCESS read-only
			STATUS current
			DESCRIPTION
				"Port name"
			::= { swi1PortTargetEntry 7 }
		
		swi1OTMData OBJECT-TYPE
			SYNTAX DisplayString
			MAX-ACCESS read-only
			STATUS current
			DESCRIPTION
				"Used to get the optical module real time data."
			::= { swi1PortTargetEntry 8 }
			
        swi1PortState OBJECT-TYPE
			SYNTAX INTEGER
				{
				linkUp(1),
				phyLinkDown(2),
				phyLinkUp(3),
				linkFault(4), 
				invalidState(255)
				}
			MAX-ACCESS read-only
			STATUS current
			DESCRIPTION
				"Port state"
			::= { swi1PortTargetEntry 9 }
			
		swi2 OBJECT IDENTIFIER ::= { swi 2 }

		
 		swi2DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { swi2 4 }
		
 		swi2Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { swi2 6 }

		
 		swi2Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"swi2Health information about a particular swi2Location. 
				This will be one of the following:
				(0-ok, 1-minor, 2-major, 3-majorandminor,4-critical,5-criticalandminor,6-criticalandmajor,7-criticalandmajorandminor)"
			::= { swi2 8 }
		
 		swi2HealthEvents OBJECT-TYPE
			SYNTAX DisplayString
			MAX-ACCESS read-only
			STATUS current
			DESCRIPTION
				"Events that contribute to the swi2Health of the swi2Location.  
				This is a list of events currently happening on the 
				swi2Location."
			::= { swi2 9 }
		
 		swi2ClearSEL OBJECT-TYPE
			SYNTAX INTEGER { clear(1) }
			MAX-ACCESS read-write
			STATUS current
			DESCRIPTION
				"Clean the BMC's SEL on the board."
			::= { swi2 12 }
		
 		swi2ConfigSupport OBJECT-TYPE
			SYNTAX DisplayString
			MAX-ACCESS read-only
			STATUS current
			DESCRIPTION
				"display the ConfigSupport of swi2."
			::= { swi2 18 }
		
 		swi2ConfigInfo OBJECT-TYPE
			SYNTAX DisplayString
			MAX-ACCESS read-only
			STATUS current
			DESCRIPTION
				"display the ConfigInfo of swi2."
			::= { swi2 19 }
		
 		swi2BladeVersion OBJECT-TYPE
			SYNTAX DisplayString
			MAX-ACCESS read-only
			STATUS current
			DESCRIPTION
				"display the Version of swi2."
			::= { swi2 20 }
		
 		swi2FcPortConn OBJECT-TYPE
			SYNTAX OCTET STRING
			MAX-ACCESS read-write
			STATUS current
			DESCRIPTION
				"Used to describe the connection of fc.
				get
				0:invalid
				1:left
				2:right
				
				set
				portid;portdirect
				(e.g.)
				(1;2)  The fc direction of port_1 is right.
				(255;1)The fc direction of all ports is left."
			::= { swi2 21 }
		
		swi2ProductName OBJECT-TYPE
			SYNTAX DisplayString
			MAX-ACCESS read-only
			STATUS current
			DESCRIPTION
				"display the Version of swi2."
			::= { swi2 22 }
			
		swi2BundleVersion OBJECT-TYPE
			SYNTAX DisplayString
			MAX-ACCESS read-write
			STATUS current
			DESCRIPTION
				"Get or set the swi2 bundle version."
			::= { swi2 23 }

		swi2ClearAlarm OBJECT-TYPE
			SYNTAX DisplayString
			MAX-ACCESS read-write
			STATUS current
			DESCRIPTION
				"Clear alarm"
			::= { swi2 24 }
 		swi2SensorTargetTable OBJECT-TYPE
			SYNTAX SEQUENCE OF Swi2SensorTargetEntry
			MAX-ACCESS not-accessible
			STATUS current
			DESCRIPTION
				"A table containing the list of sensor information."
			::= { swi2 2001 }
		
 		swi2SensorTargetEntry OBJECT-TYPE
			SYNTAX Swi2SensorTargetEntry
			MAX-ACCESS not-accessible
			STATUS current
			DESCRIPTION
				"Information about a particular current sensor."
			INDEX { swi2Target }
			::= { swi2SensorTargetTable 1 }
		
		Swi2SensorTargetEntry ::=
			SEQUENCE { 
				swi2Target
					DisplayString,
				swi2Current
					DisplayString,
				swi2ThresholdsAll
					DisplayString,
				swi2UpperCritical
					DisplayString,
				swi2UpperNonCritical
					DisplayString,
				swi2UpperNonRecoverable
					DisplayString,
				swi2LowerNonCritical
					DisplayString,
				swi2LowerCritical
					DisplayString,
				swi2LowerNonRecoverable
					DisplayString,
				swi2SensorHealth
					INTEGER,
				swi2SensorHealthEvents
					DisplayString,
				swi2NegativeHysteresis
					DisplayString,
				swi2PositiveHysteresis
					DisplayString,
				swi2SensorType
					DisplayString,
				swi2SensorFRUInfo
					DisplayString
			 }

 		swi2Target OBJECT-TYPE
			SYNTAX DisplayString
			MAX-ACCESS not-accessible
			STATUS current
			DESCRIPTION
				"sensor Name"
			::= { swi2SensorTargetEntry 1 }
		
 		swi2Current OBJECT-TYPE
			SYNTAX DisplayString
			MAX-ACCESS read-only
			STATUS current
			DESCRIPTION
				"Display the current value of a sensor."
			::= { swi2SensorTargetEntry 2 }
		
 		swi2ThresholdsAll OBJECT-TYPE
			SYNTAX DisplayString
			MAX-ACCESS read-only
			STATUS current
			DESCRIPTION
				"All thresholds of a sensor"
			::= { swi2SensorTargetEntry 3 }
		
 		swi2UpperCritical OBJECT-TYPE
			SYNTAX DisplayString
			MAX-ACCESS read-write
			STATUS current
			DESCRIPTION
				"Upper critical thresholds"
			::= { swi2SensorTargetEntry 4 }
		
 		swi2UpperNonCritical OBJECT-TYPE
			SYNTAX DisplayString
			MAX-ACCESS read-write
			STATUS current
			DESCRIPTION
				"Upper non-critical thresholds"
			::= { swi2SensorTargetEntry 5 }
		
 		swi2UpperNonRecoverable OBJECT-TYPE
			SYNTAX DisplayString
			MAX-ACCESS read-write
			STATUS current
			DESCRIPTION
				"Upper non-recoverable thresholds"
			::= { swi2SensorTargetEntry 6 }
		
 		swi2LowerNonCritical OBJECT-TYPE
			SYNTAX DisplayString
			MAX-ACCESS read-write
			STATUS current
			DESCRIPTION
				"Lower non-critical thresholds"
			::= { swi2SensorTargetEntry 7 }
		
 		swi2LowerCritical OBJECT-TYPE
			SYNTAX DisplayString
			MAX-ACCESS read-write
			STATUS current
			DESCRIPTION
				"Lower critical thresholds"
			::= { swi2SensorTargetEntry 8 }
		
 		swi2LowerNonRecoverable OBJECT-TYPE
			SYNTAX DisplayString
			MAX-ACCESS read-write
			STATUS current
			DESCRIPTION
				"Lower non-recoverable thresholds"
			::= { swi2SensorTargetEntry 9 }
		
 		swi2SensorHealth OBJECT-TYPE
			SYNTAX INTEGER
				{
				ok(0),
				minor(1),
				major(2),
				critical(3)
				}
			MAX-ACCESS read-only
			STATUS current
			DESCRIPTION
				"swi2Health information about a particular swi2Location. 
				This will be one of the following:
				(0-ok, 1-minor, 2-major, 3-critical)"
			::= { swi2SensorTargetEntry 10 }
		
 		swi2SensorHealthEvents OBJECT-TYPE
			SYNTAX DisplayString
			MAX-ACCESS read-only
			STATUS current
			DESCRIPTION
				"Events that contribute to the swi2Health of the swi2Location.  
				This is a list of events currently happening on the 
				swi2Location."
			::= { swi2SensorTargetEntry 11 }
		
		
 		swi2NegativeHysteresis OBJECT-TYPE
			SYNTAX DisplayString
			MAX-ACCESS read-write
			STATUS current
			DESCRIPTION
				"Get/Set the negativeHysteresis value"
			::= { swi2SensorTargetEntry 16 }
		
 		swi2PositiveHysteresis OBJECT-TYPE
			SYNTAX DisplayString
			MAX-ACCESS read-write
			STATUS current
			DESCRIPTION
				"Get/Set the positiveHysteresis value."
			::= { swi2SensorTargetEntry 17 }
		
 		swi2SensorType OBJECT-TYPE
			SYNTAX DisplayString
			MAX-ACCESS read-only
			STATUS current
			DESCRIPTION
				"Get the type of the sensor."
			::= { swi2SensorTargetEntry 18 }
		
 		swi2SensorFRUInfo OBJECT-TYPE
			SYNTAX DisplayString
			MAX-ACCESS read-only
			STATUS current
			DESCRIPTION
				"Get the fruinfo of the sensor."
			::= { swi2SensorTargetEntry 19 }
		
 		swi2FruTable OBJECT-TYPE
			SYNTAX SEQUENCE OF Swi2FruEntry
			MAX-ACCESS not-accessible
			STATUS current
			DESCRIPTION
				"A table containing the list of FRU information."
			::= { swi2 2002 }
		
 		swi2FruEntry OBJECT-TYPE
			SYNTAX Swi2FruEntry
			MAX-ACCESS not-accessible
			STATUS current
			DESCRIPTION
				"Information about a particular current FRU."
			INDEX { swi2fruNumber }
			::= { swi2FruTable 1 }
		
		Swi2FruEntry ::=
			SEQUENCE { 
				swi2fruNumber
					INTEGER,
				swi2FruHotSwapState
					DisplayString,
				swi2FruLedProperties
					DisplayString,
				swi2FRUControl
					INTEGER,
				swi2FRULabel
					DisplayString,
				swi2ResetReason
					DisplayString,
				swi2PowerState
					DisplayString,
				swi2SWIPControl
					DisplayString,
				swi2Gateway
					DisplayString,
				swi2Route
					DisplayString,
				swi2VLanIfIP
					DisplayString,
				swi2FruVersion
					DisplayString,
				swi2SaveConfig
					INTEGER,
				swi2StackState
					INTEGER
			 }

 		swi2fruNumber OBJECT-TYPE
			SYNTAX INTEGER
			MAX-ACCESS not-accessible
			STATUS current
			DESCRIPTION
				"Fru number"
			::= { swi2FruEntry 1 }
		
 		swi2FruHotSwapState OBJECT-TYPE
			SYNTAX DisplayString
			MAX-ACCESS read-only
			STATUS current
			DESCRIPTION
				"Retrieve the hot swap state of the FRU from the 
				internally known hot swap states of swi2."
			::= { swi2FruEntry 3 }
		
 		swi2FruLedProperties OBJECT-TYPE
			SYNTAX DisplayString
			MAX-ACCESS read-only
			STATUS current
			DESCRIPTION
				"Retrieves the LED support information from a FRU. Returns a comma separated
				list of LEDS and the number of FRU supported user LEDs."
			::= { swi2FruEntry 4 }

		

		swi2FRUControl OBJECT-TYPE
			SYNTAX INTEGER
			MAX-ACCESS read-write
			STATUS current
			DESCRIPTION
				"Set the FRU to do things like Reset, Warm Reset, etc.
				Settable value:
				'0' - reset
				'1' - warm reset"
			::= { swi2FruEntry 9 }
		
 		swi2FRULabel OBJECT-TYPE
			SYNTAX DisplayString
			MAX-ACCESS read-only
			STATUS current
			DESCRIPTION
				"Get fru label of swi2."
			::= { swi2FruEntry 10 }
		
 		swi2ResetReason OBJECT-TYPE
			SYNTAX DisplayString
			MAX-ACCESS read-only
			STATUS current
			DESCRIPTION
				"Used to get the FRU reset cause."
			::= { swi2FruEntry 11 }
		
 		swi2PowerState OBJECT-TYPE
			SYNTAX DisplayString
			MAX-ACCESS read-write
			STATUS current
			DESCRIPTION
				"The power state of a switch module.  This is used to find out 
				if a switch module is present, healthy, on/off or to shutdown and turn on 
				a switch module.   
				poweron - Power on a switch module
				poweroff - Power off a switch module"
			::= { swi2FruEntry 12 }
		
 		swi2SWIPControl OBJECT-TYPE
			SYNTAX DisplayString
			MAX-ACCESS read-write
			STATUS current
			DESCRIPTION
				"Used to get or set the base IP or fabric IP address of switch module"
			::= { swi2FruEntry 13 }
		
 		swi2Gateway OBJECT-TYPE
			SYNTAX DisplayString
			MAX-ACCESS read-write
			STATUS current
			DESCRIPTION
				"Read or set the gateway."
			::= { swi2FruEntry 14 }
		
 		swi2Route OBJECT-TYPE
			SYNTAX DisplayString
			MAX-ACCESS read-write
			STATUS current
			DESCRIPTION
				"Read or set the route."
			::= { swi2FruEntry 15 }
		
 		swi2VLanIfIP OBJECT-TYPE
			SYNTAX DisplayString
			MAX-ACCESS read-write
			STATUS current
			DESCRIPTION
				"Read or set vlanif1 IP"
			::= { swi2FruEntry 16 }
		
 		swi2FruVersion OBJECT-TYPE
			SYNTAX DisplayString
			MAX-ACCESS read-only
			STATUS current
			DESCRIPTION
				"Used to get the FRU version of the switch module."
			::= { swi2FruEntry 17 }
		
                swi2SaveConfig OBJECT-TYPE
			SYNTAX INTEGER
			MAX-ACCESS read-write
			STATUS current
			DESCRIPTION
				"Save all configurations in swi plane"
			::= { swi2FruEntry 18 }
		
		swi2StackState OBJECT-TYPE
			SYNTAX INTEGER
			MAX-ACCESS read-only
			STATUS current
			DESCRIPTION
				"Get the stack state of switch modules:
				1 -- master switch in a stack
				2 -- standby switch in a stack
				3 -- slave switch in a stack
				4 -- unstacked switch"
			::= { swi2FruEntry 19 }
		
		swi2FruLedTable OBJECT-TYPE
			SYNTAX SEQUENCE OF Swi2FruLedEntry
			MAX-ACCESS not-accessible
			STATUS current
			DESCRIPTION
				"A table containing the list of led information."
			::= { swi2 2003 }
		
 		swi2FruLedEntry OBJECT-TYPE
			SYNTAX Swi2FruLedEntry
			MAX-ACCESS not-accessible
			STATUS current
			DESCRIPTION
				"Information about a particular current led."
			INDEX { swi2FruID, swi2FruLed }
			::= { swi2FruLedTable 1 }
		
		Swi2FruLedEntry ::=
			SEQUENCE { 
				swi2FruID
					INTEGER,
				swi2FruLed
					DisplayString,
				swi2FruLedColorProps
					DisplayString,
				swi2FruLedState
					DisplayString
			 }

 		swi2FruID OBJECT-TYPE
			SYNTAX INTEGER
			MAX-ACCESS not-accessible
			STATUS current
			DESCRIPTION
				"Fru ID"
			::= { swi2FruLedEntry 1 }
		
 		swi2FruLed OBJECT-TYPE
			SYNTAX DisplayString
			MAX-ACCESS not-accessible
			STATUS current
			DESCRIPTION
				"The current FRU indicator name."
			::= { swi2FruLedEntry 2 }
		
 		swi2FruLedColorProps OBJECT-TYPE
			SYNTAX DisplayString
			MAX-ACCESS read-only
			STATUS current
			DESCRIPTION
				"Finds out what colors are supported by the LED"
			::= { swi2FruLedEntry 3 }
		
 		swi2FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { swi2FruLedEntry 4 }
		
 		swi2FruDescriptionTable OBJECT-TYPE
			SYNTAX SEQUENCE OF Swi2FruDescriptionEntry
			MAX-ACCESS not-accessible
			STATUS current
			DESCRIPTION
				"A table containing the list of swi2 FRU information."
			::= { swi2 2004 }
		
 		swi2FruDescriptionEntry OBJECT-TYPE
			SYNTAX Swi2FruDescriptionEntry
			MAX-ACCESS not-accessible
			STATUS current
			DESCRIPTION
				"Information about a particular current FRU."
			INDEX { swi2fruNum }
			::= { swi2FruDescriptionTable 1 }
		
		Swi2FruDescriptionEntry ::=
			SEQUENCE { 
				swi2fruNum
					INTEGER,
				swi2fruBoardDescription
					DisplayString,
				swi2fruBoardManufacturer
					DisplayString,
				swi2fruBoardPartNumber
					DisplayString,
				swi2fruBoardSerialNumber
					DisplayString,
				swi2fruBoardManufactureDate
					DisplayString,
				swi2fruProductDescription
					DisplayString,
				swi2fruProductManufacturer
					DisplayString,
				swi2fruProductPartNumber
					DisplayString,
				swi2fruProductSerialNumber
					DisplayString,
				swi2fruProductRevision
					DisplayString,
				swi2fruAll
					DisplayString
			 }

 		swi2fruNum OBJECT-TYPE
			SYNTAX INTEGER
			MAX-ACCESS not-accessible
			STATUS current
			DESCRIPTION
				"swi2 FRU's INDEX"
			::= { swi2FruDescriptionEntry 1 }
		
 		swi2fruBoardDescription OBJECT-TYPE
			SYNTAX DisplayString
			MAX-ACCESS read-only
			STATUS current
			DESCRIPTION
				"Used to read the Board Description from the swi2 fru."
			::= { swi2FruDescriptionEntry 2 }
		
 		swi2fruBoardManufacturer OBJECT-TYPE
			SYNTAX DisplayString
			MAX-ACCESS read-only
			STATUS current
			DESCRIPTION
				"Used to read the Board Manufacturer from the swi2 fru."
			::= { swi2FruDescriptionEntry 3 }
		
 		swi2fruBoardPartNumber OBJECT-TYPE
			SYNTAX DisplayString
			MAX-ACCESS read-only
			STATUS current
			DESCRIPTION
				"Used to read the Board Part Number from the swi2 fru."
			::= { swi2FruDescriptionEntry 4 }
		
 		swi2fruBoardSerialNumber OBJECT-TYPE
			SYNTAX DisplayString
			MAX-ACCESS read-only
			STATUS current
			DESCRIPTION
				"Used to read the Board Serial Number from the swi2 fru."
			::= { swi2FruDescriptionEntry 5 }
		
 		swi2fruBoardManufactureDate OBJECT-TYPE
			SYNTAX DisplayString
			MAX-ACCESS read-only
			STATUS current
			DESCRIPTION
				"Used to read the Board Manufacture Date from the swi2 fru."
			::= { swi2FruDescriptionEntry 6 }
		
 		swi2fruProductDescription OBJECT-TYPE
			SYNTAX DisplayString
			MAX-ACCESS read-only
			STATUS current
			DESCRIPTION
				"Used to read the Product Description from the swi2 fru."
			::= { swi2FruDescriptionEntry 7 }
		
 		swi2fruProductManufacturer OBJECT-TYPE
			SYNTAX DisplayString
			MAX-ACCESS read-only
			STATUS current
			DESCRIPTION
				"Used to read the Product Manufacturer from the swi2 fru."
			::= { swi2FruDescriptionEntry 8 }
		
 		swi2fruProductPartNumber OBJECT-TYPE
			SYNTAX DisplayString
			MAX-ACCESS read-only
			STATUS current
			DESCRIPTION
				"Used to read the Product Part Number from the swi2 fru."
			::= { swi2FruDescriptionEntry 9 }
		
 		swi2fruProductSerialNumber OBJECT-TYPE
			SYNTAX DisplayString
			MAX-ACCESS read-only
			STATUS current
			DESCRIPTION
				"Used to read the Product Serial Number from the swi2 fru."
			::= { swi2FruDescriptionEntry 10 }
		
 		swi2fruProductRevision OBJECT-TYPE
			SYNTAX DisplayString
			MAX-ACCESS read-only
			STATUS current
			DESCRIPTION
				"Used to read the Product Revision from the swi2 fru."
			::= { swi2FruDescriptionEntry 13 }
		
 		swi2fruAll OBJECT-TYPE
			SYNTAX DisplayString
			MAX-ACCESS read-only
			STATUS current
			DESCRIPTION
				"Used to read the fru info all."
			::= { swi2FruDescriptionEntry 14 }
		
 		swi2PortTargetTable OBJECT-TYPE
			SYNTAX SEQUENCE OF Swi2PortTargetEntry
			MAX-ACCESS not-accessible
			STATUS current
			DESCRIPTION
				"A table containing the list of sensor information."
			::= { swi2 2005 }
		
 		swi2PortTargetEntry OBJECT-TYPE
			SYNTAX Swi2PortTargetEntry
			MAX-ACCESS not-accessible
			STATUS current
			DESCRIPTION
				"Information about a particular current sensor."
			INDEX { swi1PortNum }
			::= { swi2PortTargetTable 1 }
		
		Swi2PortTargetEntry ::=
			SEQUENCE { 
				swi2PortNum
					INTEGER,
				swi2OTMState
					INTEGER,
				swi2OTMInfo
					DisplayString,
				swi2PhyState
					INTEGER,
				swi2PhyReset
					INTEGER,
				swi2PortToBladeSlot
					INTEGER,
				swi2PortName
					DisplayString,
				swi2OTMData
					DisplayString,
				swi2PortState
					INTEGER	
			 }

 		swi2PortNum OBJECT-TYPE
			SYNTAX INTEGER
			MAX-ACCESS read-only
			STATUS current
			DESCRIPTION
				"Port Num"
			::= { swi2PortTargetEntry 1 }
		
 		swi2OTMState OBJECT-TYPE
			SYNTAX INTEGER
				{
				not-present(0),
				present(1)
				}
			MAX-ACCESS read-only
			STATUS current
			DESCRIPTION
				"Used to get the optical module status. 
				This will be one of the following:
				(0-not present, 1-present)"
			::= { swi2PortTargetEntry 2 }
		
 		swi2OTMInfo OBJECT-TYPE
			SYNTAX DisplayString
			MAX-ACCESS read-only
			STATUS current
			DESCRIPTION
				"Used to get the optical module information."
			::= { swi2PortTargetEntry 3 }
		
 		swi2PhyState OBJECT-TYPE
			SYNTAX INTEGER
				{
				down(0),
				up(1)
				}
			MAX-ACCESS read-only
			STATUS current
			DESCRIPTION
				"Phy state"
			::= { swi2PortTargetEntry 4 }
		
 		swi2PhyReset OBJECT-TYPE
			SYNTAX INTEGER
			MAX-ACCESS write-only
			STATUS current
			DESCRIPTION
				"Phy reset"
			::= { swi2PortTargetEntry 5 }
		
 		swi2PortToBladeSlot OBJECT-TYPE
			SYNTAX INTEGER
			MAX-ACCESS read-only
			STATUS current
			DESCRIPTION
				"Used to get the server slot number"
			::= { swi2PortTargetEntry 6 }
		
 		swi2PortName OBJECT-TYPE
			SYNTAX DisplayString
			MAX-ACCESS read-only
			STATUS current
			DESCRIPTION
				"Port name"
			::= { swi2PortTargetEntry 7 }
		
		swi2OTMData OBJECT-TYPE
			SYNTAX DisplayString
			MAX-ACCESS read-only
			STATUS current
			DESCRIPTION
				"Used to get the optical module real time data."
			::= { swi2PortTargetEntry 8 }
			
		swi2PortState OBJECT-TYPE
			SYNTAX INTEGER
				{
				linkUp(1),
				phyLinkDown(2),
				phyLinkUp(3),
				linkFault(4), 
				invalidState(255)
				}
			MAX-ACCESS read-only
			STATUS current
			DESCRIPTION
				"Port state"
			::= { swi2PortTargetEntry 9 }	

		swi3 OBJECT IDENTIFIER ::= { swi 3 }

		
 		swi3DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { swi3 4 }
		
 		swi3Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { swi3 6 }

		
 		swi3Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"swi3Health information about a particular swi3Location. 
				This will be one of the following:
				(0-ok, 1-minor, 2-major, 3-majorandminor,4-critical,5-criticalandminor,6-criticalandmajor,7-criticalandmajorandminor)"
			::= { swi3 8 }
		
 		swi3HealthEvents OBJECT-TYPE
			SYNTAX DisplayString
			MAX-ACCESS read-only
			STATUS current
			DESCRIPTION
				"Events that contribute to the swi3Health of the swi3Location.  
				This is a list of events currently happening on the 
				swi3Location."
			::= { swi3 9 }
		
 		swi3ClearSEL OBJECT-TYPE
			SYNTAX INTEGER { clear(1) }
			MAX-ACCESS read-write
			STATUS current
			DESCRIPTION
				"Clean the BMC's SEL on the board."
			::= { swi3 12 }
		
 		swi3ConfigSupport OBJECT-TYPE
			SYNTAX DisplayString
			MAX-ACCESS read-only
			STATUS current
			DESCRIPTION
				"display the ConfigSupport of swi3."
			::= { swi3 18 }
		
 		swi3ConfigInfo OBJECT-TYPE
			SYNTAX DisplayString
			MAX-ACCESS read-only
			STATUS current
			DESCRIPTION
				"display the ConfigInfo of swi3."
			::= { swi3 19 }
		
 		swi3BladeVersion OBJECT-TYPE
			SYNTAX DisplayString
			MAX-ACCESS read-only
			STATUS current
			DESCRIPTION
				"display the Version of swi3."
			::= { swi3 20 }
		
 		swi3FcPortConn OBJECT-TYPE
			SYNTAX OCTET STRING
			MAX-ACCESS read-write
			STATUS current
			DESCRIPTION
				"Used to describe the connection of fc.
				get
				0:invalid
				1:left
				2:right
				
				set
				portid;portdirect
				(e.g.)
				(1;2)  The fc direction of port_1 is right.
				(255;1)The fc direction of all ports is left."
			::= { swi3 21 }
		
		swi3ProductName OBJECT-TYPE
			SYNTAX DisplayString
			MAX-ACCESS read-only
			STATUS current
			DESCRIPTION
				"display the Version of swi3."
			::= { swi3 22 }
			
		swi3BundleVersion OBJECT-TYPE
			SYNTAX DisplayString
			MAX-ACCESS read-write
			STATUS current
			DESCRIPTION
				"Get or set the swi3 bundle version."
			::= { swi3 23 }

		swi3ClearAlarm OBJECT-TYPE
			SYNTAX DisplayString
			MAX-ACCESS read-write
			STATUS current
			DESCRIPTION
				"Clear alarm"
			::= { swi3 24 }
 		swi3SensorTargetTable OBJECT-TYPE
			SYNTAX SEQUENCE OF Swi3SensorTargetEntry
			MAX-ACCESS not-accessible
			STATUS current
			DESCRIPTION
				"A table containing the list of sensor information."
			::= { swi3 2001 }
		
 		swi3SensorTargetEntry OBJECT-TYPE
			SYNTAX Swi3SensorTargetEntry
			MAX-ACCESS not-accessible
			STATUS current
			DESCRIPTION
				"Information about a particular current sensor."
			INDEX { swi3Target }
			::= { swi3SensorTargetTable 1 }
		
		Swi3SensorTargetEntry ::=
			SEQUENCE { 
				swi3Target
					DisplayString,
				swi3Current
					DisplayString,
				swi3ThresholdsAll
					DisplayString,
				swi3UpperCritical
					DisplayString,
				swi3UpperNonCritical
					DisplayString,
				swi3UpperNonRecoverable
					DisplayString,
				swi3LowerNonCritical
					DisplayString,
				swi3LowerCritical
					DisplayString,
				swi3LowerNonRecoverable
					DisplayString,
				swi3SensorHealth
					INTEGER,
				swi3SensorHealthEvents
					DisplayString,
				swi3NegativeHysteresis
					DisplayString,
				swi3PositiveHysteresis
					DisplayString,
				swi3SensorType
					DisplayString,
				swi3SensorFRUInfo
					DisplayString
			 }

 		swi3Target OBJECT-TYPE
			SYNTAX DisplayString
			MAX-ACCESS not-accessible
			STATUS current
			DESCRIPTION
				"sensor Name"
			::= { swi3SensorTargetEntry 1 }
		
 		swi3Current OBJECT-TYPE
			SYNTAX DisplayString
			MAX-ACCESS read-only
			STATUS current
			DESCRIPTION
				"Display the current value of a sensor."
			::= { swi3SensorTargetEntry 2 }
		
 		swi3ThresholdsAll OBJECT-TYPE
			SYNTAX DisplayString
			MAX-ACCESS read-only
			STATUS current
			DESCRIPTION
				"All thresholds of a sensor"
			::= { swi3SensorTargetEntry 3 }
		
 		swi3UpperCritical OBJECT-TYPE
			SYNTAX DisplayString
			MAX-ACCESS read-write
			STATUS current
			DESCRIPTION
				"Upper critical thresholds"
			::= { swi3SensorTargetEntry 4 }
		
 		swi3UpperNonCritical OBJECT-TYPE
			SYNTAX DisplayString
			MAX-ACCESS read-write
			STATUS current
			DESCRIPTION
				"Upper non-critical thresholds"
			::= { swi3SensorTargetEntry 5 }
		
 		swi3UpperNonRecoverable OBJECT-TYPE
			SYNTAX DisplayString
			MAX-ACCESS read-write
			STATUS current
			DESCRIPTION
				"Upper non-recoverable thresholds"
			::= { swi3SensorTargetEntry 6 }
		
 		swi3LowerNonCritical OBJECT-TYPE
			SYNTAX DisplayString
			MAX-ACCESS read-write
			STATUS current
			DESCRIPTION
				"Lower non-critical thresholds"
			::= { swi3SensorTargetEntry 7 }
		
 		swi3LowerCritical OBJECT-TYPE
			SYNTAX DisplayString
			MAX-ACCESS read-write
			STATUS current
			DESCRIPTION
				"Lower critical thresholds"
			::= { swi3SensorTargetEntry 8 }
		
 		swi3LowerNonRecoverable OBJECT-TYPE
			SYNTAX DisplayString
			MAX-ACCESS read-write
			STATUS current
			DESCRIPTION
				"Lower non-recoverable thresholds"
			::= { swi3SensorTargetEntry 9 }
		
 		swi3SensorHealth OBJECT-TYPE
			SYNTAX INTEGER
				{
				ok(0),
				minor(1),
				major(2),
				critical(3)
				}
			MAX-ACCESS read-only
			STATUS current
			DESCRIPTION
				"swi3Health information about a particular swi3Location. 
				This will be one of the following:
				(0-ok, 1-minor, 2-major, 3-critical)"
			::= { swi3SensorTargetEntry 10 }
		
 		swi3SensorHealthEvents OBJECT-TYPE
			SYNTAX DisplayString
			MAX-ACCESS read-only
			STATUS current
			DESCRIPTION
				"Events that contribute to the swi3Health of the swi3Location.  
				This is a list of events currently happening on the 
				swi3Location."
			::= { swi3SensorTargetEntry 11 }
		
		
 		swi3NegativeHysteresis OBJECT-TYPE
			SYNTAX DisplayString
			MAX-ACCESS read-write
			STATUS current
			DESCRIPTION
				"Get/Set the negativeHysteresis value"
			::= { swi3SensorTargetEntry 16 }
		
 		swi3PositiveHysteresis OBJECT-TYPE
			SYNTAX DisplayString
			MAX-ACCESS read-write
			STATUS current
			DESCRIPTION
				"Get/Set the positiveHysteresis value."
			::= { swi3SensorTargetEntry 17 }
		
 		swi3SensorType OBJECT-TYPE
			SYNTAX DisplayString
			MAX-ACCESS read-only
			STATUS current
			DESCRIPTION
				"Get the type of the sensor."
			::= { swi3SensorTargetEntry 18 }
		
 		swi3SensorFRUInfo OBJECT-TYPE
			SYNTAX DisplayString
			MAX-ACCESS read-only
			STATUS current
			DESCRIPTION
				"Get the fruinfo of the sensor."
			::= { swi3SensorTargetEntry 19 }
		
 		swi3FruTable OBJECT-TYPE
			SYNTAX SEQUENCE OF Swi3FruEntry
			MAX-ACCESS not-accessible
			STATUS current
			DESCRIPTION
				"A table containing the list of FRU information."
			::= { swi3 2002 }
		
 		swi3FruEntry OBJECT-TYPE
			SYNTAX Swi3FruEntry
			MAX-ACCESS not-accessible
			STATUS current
			DESCRIPTION
				"Information about a particular current FRU."
			INDEX { swi3fruNumber }
			::= { swi3FruTable 1 }
		
		Swi3FruEntry ::=
			SEQUENCE { 
				swi3fruNumber
					INTEGER,
				swi3FruHotSwapState
					DisplayString,
				swi3FruLedProperties
					DisplayString,
				swi3FRUControl
					INTEGER,
				swi3FRULabel
					DisplayString,
				swi3ResetReason
					DisplayString,
				swi3PowerState
					DisplayString,
				swi3SWIPControl
					DisplayString,
				swi3Gateway
					DisplayString,
				swi3Route
					DisplayString,
				swi3VLanIfIP
					DisplayString,
				swi3FruVersion
					DisplayString,
				swi3SaveConfig
					INTEGER,
				swi3StackState
					INTEGER
			 }

 		swi3fruNumber OBJECT-TYPE
			SYNTAX INTEGER
			MAX-ACCESS not-accessible
			STATUS current
			DESCRIPTION
				"Fru number"
			::= { swi3FruEntry 1 }
		
 		swi3FruHotSwapState OBJECT-TYPE
			SYNTAX DisplayString
			MAX-ACCESS read-only
			STATUS current
			DESCRIPTION
				"Retrieve the hot swap state of the FRU from the 
				internally known hot swap states of swi3."
			::= { swi3FruEntry 3 }
		
 		swi3FruLedProperties OBJECT-TYPE
			SYNTAX DisplayString
			MAX-ACCESS read-only
			STATUS current
			DESCRIPTION
				"Retrieves the LED support information from a FRU. Returns a comma separated
				list of LEDS and the number of FRU supported user LEDs."
			::= { swi3FruEntry 4 }

		

		swi3FRUControl OBJECT-TYPE
			SYNTAX INTEGER
			MAX-ACCESS read-write
			STATUS current
			DESCRIPTION
				"Set the FRU to do things like Reset, Warm Reset, etc.
				Settable value:
				'0' - reset
				'1' - warm reset"
			::= { swi3FruEntry 9 }
		
 		swi3FRULabel OBJECT-TYPE
			SYNTAX DisplayString
			MAX-ACCESS read-only
			STATUS current
			DESCRIPTION
				"Get fru label of swi3."
			::= { swi3FruEntry 10 }
		
 		swi3ResetReason OBJECT-TYPE
			SYNTAX DisplayString
			MAX-ACCESS read-only
			STATUS current
			DESCRIPTION
				"Used to get the FRU reset cause."
			::= { swi3FruEntry 11 }
		
 		swi3PowerState OBJECT-TYPE
			SYNTAX DisplayString
			MAX-ACCESS read-write
			STATUS current
			DESCRIPTION
				"The power state of a switch module. This is used to find out 
				if a switch module is present, healthy, on/off or to shutdown and turn on 
				a switch module.
				poweron - Power on a switch module
				poweroff - Power off a switch module"
			::= { swi3FruEntry 12 }
		
 		swi3SWIPControl OBJECT-TYPE
			SYNTAX DisplayString
			MAX-ACCESS read-write
			STATUS current
			DESCRIPTION
				"Used to get or set the base IP or fabric IP address of switch module"
			::= { swi3FruEntry 13 }
		
 		swi3Gateway OBJECT-TYPE
			SYNTAX DisplayString
			MAX-ACCESS read-write
			STATUS current
			DESCRIPTION
				"Read or set the gateway."
			::= { swi3FruEntry 14 }
		
 		swi3Route OBJECT-TYPE
			SYNTAX DisplayString
			MAX-ACCESS read-write
			STATUS current
			DESCRIPTION
				"Read or set the route."
			::= { swi3FruEntry 15 }
		
 		swi3VLanIfIP OBJECT-TYPE
			SYNTAX DisplayString
			MAX-ACCESS read-write
			STATUS current
			DESCRIPTION
				"Read or set vlanif1 IP"
			::= { swi3FruEntry 16 }
		
 		swi3FruVersion OBJECT-TYPE
			SYNTAX DisplayString
			MAX-ACCESS read-only
			STATUS current
			DESCRIPTION
				"Used to get the FRU version of the switch module."
			::= { swi3FruEntry 17 }
		
                swi3SaveConfig OBJECT-TYPE
			SYNTAX INTEGER
			MAX-ACCESS read-write
			STATUS current
			DESCRIPTION
				"Save all configurations in swi plane"
			::= { swi3FruEntry 18 }
		
		swi3StackState OBJECT-TYPE
			SYNTAX INTEGER
			MAX-ACCESS read-only
			STATUS current
			DESCRIPTION
				"Get the stack state of switch modules:
				1 -- master switch in a stack
				2 -- standby switch in a stack
				3 -- slave switch in a stack
				4 -- unstacked switch"
			::= { swi3FruEntry 19 }
		
		swi3FruLedTable OBJECT-TYPE
			SYNTAX SEQUENCE OF Swi3FruLedEntry
			MAX-ACCESS not-accessible
			STATUS current
			DESCRIPTION
				"A table containing the list of led information."
			::= { swi3 2003 }
		
 		swi3FruLedEntry OBJECT-TYPE
			SYNTAX Swi3FruLedEntry
			MAX-ACCESS not-accessible
			STATUS current
			DESCRIPTION
				"Information about a particular current led."
			INDEX { swi3FruID, swi3FruLed }
			::= { swi3FruLedTable 1 }
		
		Swi3FruLedEntry ::=
			SEQUENCE { 
				swi3FruID
					INTEGER,
				swi3FruLed
					DisplayString,
				swi3FruLedColorProps
					DisplayString,
				swi3FruLedState
					DisplayString
			 }

 		swi3FruID OBJECT-TYPE
			SYNTAX INTEGER
			MAX-ACCESS not-accessible
			STATUS current
			DESCRIPTION
				"Fru ID"
			::= { swi3FruLedEntry 1 }
		
 		swi3FruLed OBJECT-TYPE
			SYNTAX DisplayString
			MAX-ACCESS not-accessible
			STATUS current
			DESCRIPTION
				"The current FRU indicator name."
			::= { swi3FruLedEntry 2 }
		
 		swi3FruLedColorProps OBJECT-TYPE
			SYNTAX DisplayString
			MAX-ACCESS read-only
			STATUS current
			DESCRIPTION
				"Finds out what colors are supported by the LED"
			::= { swi3FruLedEntry 3 }
		
 		swi3FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { swi3FruLedEntry 4 }
		
 		swi3FruDescriptionTable OBJECT-TYPE
			SYNTAX SEQUENCE OF Swi3FruDescriptionEntry
			MAX-ACCESS not-accessible
			STATUS current
			DESCRIPTION
				"A table containing the list of swi3 FRU information."
			::= { swi3 2004 }
		
 		swi3FruDescriptionEntry OBJECT-TYPE
			SYNTAX Swi3FruDescriptionEntry
			MAX-ACCESS not-accessible
			STATUS current
			DESCRIPTION
				"Information about a particular current FRU."
			INDEX { swi3fruNum }
			::= { swi3FruDescriptionTable 1 }
		
		Swi3FruDescriptionEntry ::=
			SEQUENCE { 
				swi3fruNum
					INTEGER,
				swi3fruBoardDescription
					DisplayString,
				swi3fruBoardManufacturer
					DisplayString,
				swi3fruBoardPartNumber
					DisplayString,
				swi3fruBoardSerialNumber
					DisplayString,
				swi3fruBoardManufactureDate
					DisplayString,
				swi3fruProductDescription
					DisplayString,
				swi3fruProductManufacturer
					DisplayString,
				swi3fruProductPartNumber
					DisplayString,
				swi3fruProductSerialNumber
					DisplayString,
				swi3fruProductRevision
					DisplayString,
				swi3fruAll
					DisplayString
			 }

 		swi3fruNum OBJECT-TYPE
			SYNTAX INTEGER
			MAX-ACCESS not-accessible
			STATUS current
			DESCRIPTION
				"swi3 FRU's INDEX"
			::= { swi3FruDescriptionEntry 1 }
		
 		swi3fruBoardDescription OBJECT-TYPE
			SYNTAX DisplayString
			MAX-ACCESS read-only
			STATUS current
			DESCRIPTION
				"Used to read the Board Description from the swi3 fru."
			::= { swi3FruDescriptionEntry 2 }
		
 		swi3fruBoardManufacturer OBJECT-TYPE
			SYNTAX DisplayString
			MAX-ACCESS read-only
			STATUS current
			DESCRIPTION
				"Used to read the Board Manufacturer from the swi3 fru."
			::= { swi3FruDescriptionEntry 3 }
		
 		swi3fruBoardPartNumber OBJECT-TYPE
			SYNTAX DisplayString
			MAX-ACCESS read-only
			STATUS current
			DESCRIPTION
				"Used to read the Board Part Number from the swi3 fru."
			::= { swi3FruDescriptionEntry 4 }
		
 		swi3fruBoardSerialNumber OBJECT-TYPE
			SYNTAX DisplayString
			MAX-ACCESS read-only
			STATUS current
			DESCRIPTION
				"Used to read the Board Serial Number from the swi3 fru."
			::= { swi3FruDescriptionEntry 5 }
		
 		swi3fruBoardManufactureDate OBJECT-TYPE
			SYNTAX DisplayString
			MAX-ACCESS read-only
			STATUS current
			DESCRIPTION
				"Used to read the Board Manufacture Date from the swi3 fru."
			::= { swi3FruDescriptionEntry 6 }
		
 		swi3fruProductDescription OBJECT-TYPE
			SYNTAX DisplayString
			MAX-ACCESS read-only
			STATUS current
			DESCRIPTION
				"Used to read the Product Description from the swi3 fru."
			::= { swi3FruDescriptionEntry 7 }
		
 		swi3fruProductManufacturer OBJECT-TYPE
			SYNTAX DisplayString
			MAX-ACCESS read-only
			STATUS current
			DESCRIPTION
				"Used to read the Product Manufacturer from the swi3 fru."
			::= { swi3FruDescriptionEntry 8 }
		
 		swi3fruProductPartNumber OBJECT-TYPE
			SYNTAX DisplayString
			MAX-ACCESS read-only
			STATUS current
			DESCRIPTION
				"Used to read the Product Part Number from the swi3 fru."
			::= { swi3FruDescriptionEntry 9 }
		
 		swi3fruProductSerialNumber OBJECT-TYPE
			SYNTAX DisplayString
			MAX-ACCESS read-only
			STATUS current
			DESCRIPTION
				"Used to read the Product Serial Number from the swi3 fru."
			::= { swi3FruDescriptionEntry 10 }
		
 		swi3fruProductRevision OBJECT-TYPE
			SYNTAX DisplayString
			MAX-ACCESS read-only
			STATUS current
			DESCRIPTION
				"Used to read the Product Revision from the swi3 fru."
			::= { swi3FruDescriptionEntry 13 }
		
 		swi3fruAll OBJECT-TYPE
			SYNTAX DisplayString
			MAX-ACCESS read-only
			STATUS current
			DESCRIPTION
				"Used to read the fru info all."
			::= { swi3FruDescriptionEntry 14 }
		
 		swi3PortTargetTable OBJECT-TYPE
			SYNTAX SEQUENCE OF Swi3PortTargetEntry
			MAX-ACCESS not-accessible
			STATUS current
			DESCRIPTION
				"A table containing the list of sensor information."
			::= { swi3 2005 }
		
 		swi3PortTargetEntry OBJECT-TYPE
			SYNTAX Swi3PortTargetEntry
			MAX-ACCESS not-accessible
			STATUS current
			DESCRIPTION
				"Information about a particular current sensor."
			INDEX { swi1PortNum }
			::= { swi3PortTargetTable 1 }
		
		Swi3PortTargetEntry ::=
			SEQUENCE { 
				swi3PortNum
					INTEGER,
				swi3OTMState
					INTEGER,
				swi3OTMInfo
					DisplayString,
				swi3PhyState
					INTEGER,
				swi3PhyReset
					INTEGER,
				swi3PortToBladeSlot
					INTEGER,
				swi3PortName
					DisplayString,
				swi3OTMData
					DisplayString,
				swi3PortState
					INTEGER	
			 }

 		swi3PortNum OBJECT-TYPE
			SYNTAX INTEGER
			MAX-ACCESS read-only
			STATUS current
			DESCRIPTION
				"Port Num"
			::= { swi3PortTargetEntry 1 }
		
 		swi3OTMState OBJECT-TYPE
			SYNTAX INTEGER
				{
				not-present(0),
				present(1)
				}
			MAX-ACCESS read-only
			STATUS current
			DESCRIPTION
				"Used to get the optical module status. 
				This will be one of the following:
				(0-not present, 1-present)"
			::= { swi3PortTargetEntry 2 }
		
 		swi3OTMInfo OBJECT-TYPE
			SYNTAX DisplayString
			MAX-ACCESS read-only
			STATUS current
			DESCRIPTION
				"Used to get the optical module information."
			::= { swi3PortTargetEntry 3 }
		
 		swi3PhyState OBJECT-TYPE
			SYNTAX INTEGER
				{
				down(0),
				up(1)
				}
			MAX-ACCESS read-only
			STATUS current
			DESCRIPTION
				"Phy state"
			::= { swi3PortTargetEntry 4 }
		
 		swi3PhyReset OBJECT-TYPE
			SYNTAX INTEGER
			MAX-ACCESS write-only
			STATUS current
			DESCRIPTION
				"Phy reset"
			::= { swi3PortTargetEntry 5 }
		
 		swi3PortToBladeSlot OBJECT-TYPE
			SYNTAX INTEGER
			MAX-ACCESS read-only
			STATUS current
			DESCRIPTION
				"Used to get the server slot number."
			::= { swi3PortTargetEntry 6 }
		
 		swi3PortName OBJECT-TYPE
			SYNTAX DisplayString
			MAX-ACCESS read-only
			STATUS current
			DESCRIPTION
				"Port name"
			::= { swi3PortTargetEntry 7 }
		
		swi3OTMData OBJECT-TYPE
			SYNTAX DisplayString
			MAX-ACCESS read-only
			STATUS current
			DESCRIPTION
				"Used to get the optical module real time data."
			::= { swi3PortTargetEntry 8 }
			
		swi3PortState OBJECT-TYPE
			SYNTAX INTEGER
				{
				linkUp(1),
				phyLinkDown(2),
				phyLinkUp(3),
				linkFault(4), 
				invalidState(255)
				}
			MAX-ACCESS read-only
			STATUS current
			DESCRIPTION
				"Port state"
			::= { swi3PortTargetEntry 9 }	

		swi4 OBJECT IDENTIFIER ::= { swi 4 }

		
 		swi4DeviceID OBJECT-TYPE
			SYNTAX DisplayString
			MAX-ACCESS read-only
			STATUS current
			DESCRIPTION
				"Display the contents of the DEVICE ID information.  
				The fields are space separated:
				Field 1 - Device ID                   
				Field 2 - SDR Support
				Field 3 - Device Revision
				Field 4 - Device Available
				Field 5 - Firmware Revision
				Field 6 - IPMI Version
				Field 7 - shelf Support
				Field 8 - Bridge Support
				Field 9 - IPMB Event Generator Support
				Field 10 - IPMB Event Receiver Support
				Field 11 - FRU Inventory Support
				Field 12 - SEL Support
				Field 13 - SDR Repository Support
				Field 14 - Sensor Support
				Field 15 - Manufacturer ID
				Field 16 - Product ID
				Field 17 - Aux Firmware Revision
				"
			::= { swi4 4 }
		
 		swi4Presence OBJECT-TYPE
			SYNTAX INTEGER
				{
				not-present(0),
				present(1),
				indeterminate(2)
				}
			MAX-ACCESS read-only
			STATUS current
			DESCRIPTION
				"Used to find out if a Location is present in the shelf.
				0 - not present
				1 - present
				2 - indeterminate"
			::= { swi4 6 }

		
 		swi4Health OBJECT-TYPE
			SYNTAX INTEGER
				{
				ok(0),
				minor(1),
				major(2),
				majorandminor(3),
				critical(4),
				criticalandminor(5),
				criticalandmajor(6),
				criticalandmajorandminor(7)
				}
			MAX-ACCESS read-only
			STATUS current
			DESCRIPTION
				"swi4Health information about a particular swi4Location. 
				This will be one of the following:
				(0-ok, 1-minor, 2-major, 3-majorandminor,4-critical,5-criticalandminor,6-criticalandmajor,7-criticalandmajorandminor)"
			::= { swi4 8 }
		
 		swi4HealthEvents OBJECT-TYPE
			SYNTAX DisplayString
			MAX-ACCESS read-only
			STATUS current
			DESCRIPTION
				"Events that contribute to the swi4Health of the swi4Location.  
				This is a list of events currently happening on the 
				swi4Location."
			::= { swi4 9 }
		
 		swi4ClearSEL OBJECT-TYPE
			SYNTAX INTEGER { clear(1) }
			MAX-ACCESS read-write
			STATUS current
			DESCRIPTION
				"Clean the BMC's SEL on the board."
			::= { swi4 12 }
		
 		swi4ConfigSupport OBJECT-TYPE
			SYNTAX DisplayString
			MAX-ACCESS read-only
			STATUS current
			DESCRIPTION
				"display the ConfigSupport of swi4."
			::= { swi4 18 }
		
 		swi4ConfigInfo OBJECT-TYPE
			SYNTAX DisplayString
			MAX-ACCESS read-only
			STATUS current
			DESCRIPTION
				"display the ConfigInfo of swi4."
			::= { swi4 19 }
		
 		swi4BladeVersion OBJECT-TYPE
			SYNTAX DisplayString
			MAX-ACCESS read-only
			STATUS current
			DESCRIPTION
				"display the Version of swi4."
			::= { swi4 20 }
		
 		swi4FcPortConn OBJECT-TYPE
			SYNTAX OCTET STRING
			MAX-ACCESS read-write
			STATUS current
			DESCRIPTION
				"Used to describe the connection of fc.
				get
				0:invalid
				1:left
				2:right
				
				set
				portid;portdirect
				(e.g.)
				(1;2)  The fc direction of port_1 is right.
				(255;1)The fc direction of all ports is left."
			::= { swi4 21 }
		
		swi4ProductName OBJECT-TYPE
			SYNTAX DisplayString
			MAX-ACCESS read-only
			STATUS current
			DESCRIPTION
				"display the Version of swi4."
			::= { swi4 22 }
			
		swi4BundleVersion OBJECT-TYPE
			SYNTAX DisplayString
			MAX-ACCESS read-write
			STATUS current
			DESCRIPTION
				"Get or set the swi4 bundle version."
			::= { swi4 23 }

		swi4ClearAlarm OBJECT-TYPE
			SYNTAX DisplayString
			MAX-ACCESS read-write
			STATUS current
			DESCRIPTION
				"Clear alarm"
			::= { swi4 24 }
 		swi4SensorTargetTable OBJECT-TYPE
			SYNTAX SEQUENCE OF Swi4SensorTargetEntry
			MAX-ACCESS not-accessible
			STATUS current
			DESCRIPTION
				"A table containing the list of sensor information."
			::= { swi4 2001 }
		
 		swi4SensorTargetEntry OBJECT-TYPE
			SYNTAX Swi4SensorTargetEntry
			MAX-ACCESS not-accessible
			STATUS current
			DESCRIPTION
				"Information about a particular current sensor."
			INDEX { swi4Target }
			::= { swi4SensorTargetTable 1 }
		
		Swi4SensorTargetEntry ::=
			SEQUENCE { 
				swi4Target
					DisplayString,
				swi4Current
					DisplayString,
				swi4ThresholdsAll
					DisplayString,
				swi4UpperCritical
					DisplayString,
				swi4UpperNonCritical
					DisplayString,
				swi4UpperNonRecoverable
					DisplayString,
				swi4LowerNonCritical
					DisplayString,
				swi4LowerCritical
					DisplayString,
				swi4LowerNonRecoverable
					DisplayString,
				swi4SensorHealth
					INTEGER,
				swi4SensorHealthEvents
					DisplayString,
				swi4NegativeHysteresis
					DisplayString,
				swi4PositiveHysteresis
					DisplayString,
				swi4SensorType
					DisplayString,
				swi4SensorFRUInfo
					DisplayString
			 }

 		swi4Target OBJECT-TYPE
			SYNTAX DisplayString
			MAX-ACCESS not-accessible
			STATUS current
			DESCRIPTION
				"sensor Name"
			::= { swi4SensorTargetEntry 1 }
		
 		swi4Current OBJECT-TYPE
			SYNTAX DisplayString
			MAX-ACCESS read-only
			STATUS current
			DESCRIPTION
				"Display the current value of a sensor."
			::= { swi4SensorTargetEntry 2 }
		
 		swi4ThresholdsAll OBJECT-TYPE
			SYNTAX DisplayString
			MAX-ACCESS read-only
			STATUS current
			DESCRIPTION
				"All thresholds of a sensor"
			::= { swi4SensorTargetEntry 3 }
		
 		swi4UpperCritical OBJECT-TYPE
			SYNTAX DisplayString
			MAX-ACCESS read-write
			STATUS current
			DESCRIPTION
				"Upper critical thresholds"
			::= { swi4SensorTargetEntry 4 }
		
 		swi4UpperNonCritical OBJECT-TYPE
			SYNTAX DisplayString
			MAX-ACCESS read-write
			STATUS current
			DESCRIPTION
				"Upper non-critical thresholds"
			::= { swi4SensorTargetEntry 5 }
		
 		swi4UpperNonRecoverable OBJECT-TYPE
			SYNTAX DisplayString
			MAX-ACCESS read-write
			STATUS current
			DESCRIPTION
				"Upper non-recoverable thresholds"
			::= { swi4SensorTargetEntry 6 }
		
 		swi4LowerNonCritical OBJECT-TYPE
			SYNTAX DisplayString
			MAX-ACCESS read-write
			STATUS current
			DESCRIPTION
				"Lower non-critical thresholds"
			::= { swi4SensorTargetEntry 7 }
		
 		swi4LowerCritical OBJECT-TYPE
			SYNTAX DisplayString
			MAX-ACCESS read-write
			STATUS current
			DESCRIPTION
				"Lower critical thresholds"
			::= { swi4SensorTargetEntry 8 }
		
 		swi4LowerNonRecoverable OBJECT-TYPE
			SYNTAX DisplayString
			MAX-ACCESS read-write
			STATUS current
			DESCRIPTION
				"Lower non-recoverable thresholds"
			::= { swi4SensorTargetEntry 9 }
		
 		swi4SensorHealth OBJECT-TYPE
			SYNTAX INTEGER
				{
				ok(0),
				minor(1),
				major(2),
				critical(3)
				}
			MAX-ACCESS read-only
			STATUS current
			DESCRIPTION
				"swi4Health information about a particular swi4Location. 
				This will be one of the following:
				(0-ok, 1-minor, 2-major, 3-critical)"
			::= { swi4SensorTargetEntry 10 }
		
 		swi4SensorHealthEvents OBJECT-TYPE
			SYNTAX DisplayString
			MAX-ACCESS read-only
			STATUS current
			DESCRIPTION
				"Events that contribute to the swi4Health of the swi4Location.  
				This is a list of events currently happening on the 
				swi4Location."
			::= { swi4SensorTargetEntry 11 }
		
		
 		swi4NegativeHysteresis OBJECT-TYPE
			SYNTAX DisplayString
			MAX-ACCESS read-write
			STATUS current
			DESCRIPTION
				"Get/Set the negativeHysteresis value"
			::= { swi4SensorTargetEntry 16 }
		
 		swi4PositiveHysteresis OBJECT-TYPE
			SYNTAX DisplayString
			MAX-ACCESS read-write
			STATUS current
			DESCRIPTION
				"Get/Set the positiveHysteresis value."
			::= { swi4SensorTargetEntry 17 }
		
 		swi4SensorType OBJECT-TYPE
			SYNTAX DisplayString
			MAX-ACCESS read-only
			STATUS current
			DESCRIPTION
				"Get the type of the sensor."
			::= { swi4SensorTargetEntry 18 }
		
 		swi4SensorFRUInfo OBJECT-TYPE
			SYNTAX DisplayString
			MAX-ACCESS read-only
			STATUS current
			DESCRIPTION
				"Get the fruinfo of the sensor."
			::= { swi4SensorTargetEntry 19 }
		
 		swi4FruTable OBJECT-TYPE
			SYNTAX SEQUENCE OF Swi4FruEntry
			MAX-ACCESS not-accessible
			STATUS current
			DESCRIPTION
				"A table containing the list of FRU information."
			::= { swi4 2002 }
		
 		swi4FruEntry OBJECT-TYPE
			SYNTAX Swi4FruEntry
			MAX-ACCESS not-accessible
			STATUS current
			DESCRIPTION
				"Information about a particular current FRU."
			INDEX { swi4fruNumber }
			::= { swi4FruTable 1 }
		
		Swi4FruEntry ::=
			SEQUENCE { 
				swi4fruNumber
					INTEGER,
				swi4FruHotSwapState
					DisplayString,
				swi4FruLedProperties
					DisplayString,
				swi4FRUControl
					INTEGER,
				swi4FRULabel
					DisplayString,
				swi4ResetReason
					DisplayString,
				swi4PowerState
					DisplayString,
				swi4SWIPControl
					DisplayString,
				swi4Gateway
					DisplayString,
				swi4Route
					DisplayString,
				swi4VLanIfIP
					DisplayString,
				swi4FruVersion
					DisplayString,
				swi4SaveConfig
					INTEGER,
				swi4StackState
					INTEGER
			 }

 		swi4fruNumber OBJECT-TYPE
			SYNTAX INTEGER
			MAX-ACCESS not-accessible
			STATUS current
			DESCRIPTION
				"Fru number"
			::= { swi4FruEntry 1 }
		
 		swi4FruHotSwapState OBJECT-TYPE
			SYNTAX DisplayString
			MAX-ACCESS read-only
			STATUS current
			DESCRIPTION
				"Retrieve the hot swap state of the FRU from the 
				internally known hot swap states of swi4."
			::= { swi4FruEntry 3 }
		
 		swi4FruLedProperties OBJECT-TYPE
			SYNTAX DisplayString
			MAX-ACCESS read-only
			STATUS current
			DESCRIPTION
				"Retrieves the LED support information from a FRU. Returns a comma separated
				list of LEDS and the number of FRU supported user LEDs."
			::= { swi4FruEntry 4 }

		

		swi4FRUControl OBJECT-TYPE
			SYNTAX INTEGER
			MAX-ACCESS read-write
			STATUS current
			DESCRIPTION
				"Set the FRU to do things like Reset, Warm Reset, etc.
				Settable value:
				'0' - reset
				'1' - warm reset"
			::= { swi4FruEntry 9 }
		
 		swi4FRULabel OBJECT-TYPE
			SYNTAX DisplayString
			MAX-ACCESS read-only
			STATUS current
			DESCRIPTION
				"Get fru label of swi4."
			::= { swi4FruEntry 10 }
		
 		swi4ResetReason OBJECT-TYPE
			SYNTAX DisplayString
			MAX-ACCESS read-only
			STATUS current
			DESCRIPTION
				"Used to get the FRU reset cause."
			::= { swi4FruEntry 11 }
		
 		swi4PowerState OBJECT-TYPE
			SYNTAX DisplayString
			MAX-ACCESS read-write
			STATUS current
			DESCRIPTION
				"The power state of a switch module.  This is used to find out 
				if a switch module is present, healthy, on/off or to shutdown and turn on 
				a switch module.
				poweron - Power on a switch module
				poweroff - Power off a switch module"
			::= { swi4FruEntry 12 }
		
 		swi4SWIPControl OBJECT-TYPE
			SYNTAX DisplayString
			MAX-ACCESS read-write
			STATUS current
			DESCRIPTION
				"Used to get or set the base IP or fabric IP address of switch module"
			::= { swi4FruEntry 13 }
		
 		swi4Gateway OBJECT-TYPE
			SYNTAX DisplayString
			MAX-ACCESS read-write
			STATUS current
			DESCRIPTION
				"Read or set the gateway."
			::= { swi4FruEntry 14 }
		
 		swi4Route OBJECT-TYPE
			SYNTAX DisplayString
			MAX-ACCESS read-write
			STATUS current
			DESCRIPTION
				"Read or set the route."
			::= { swi4FruEntry 15 }
		
 		swi4VLanIfIP OBJECT-TYPE
			SYNTAX DisplayString
			MAX-ACCESS read-write
			STATUS current
			DESCRIPTION
				"Read or set vlanif1 IP"
			::= { swi4FruEntry 16 }
		
 		swi4FruVersion OBJECT-TYPE
			SYNTAX DisplayString
			MAX-ACCESS read-only
			STATUS current
			DESCRIPTION
				"Used to get the FRU version of the switch module."
			::= { swi4FruEntry 17 }
		
               swi4SaveConfig OBJECT-TYPE
			SYNTAX INTEGER
			MAX-ACCESS read-write
			STATUS current
			DESCRIPTION
				"Save all configurations in swi plane"
			::= { swi4FruEntry 18 }
		
		swi4StackState OBJECT-TYPE
			SYNTAX INTEGER
			MAX-ACCESS read-only
			STATUS current
			DESCRIPTION
				"Get the stack state of switch modules:
				1 -- master switch in a stack
				2 -- standby switch in a stack
				3 -- slave switch in a stack
				4 -- unstacked switch"
			::= { swi4FruEntry 19 }
		
		swi4FruLedTable OBJECT-TYPE
			SYNTAX SEQUENCE OF Swi4FruLedEntry
			MAX-ACCESS not-accessible
			STATUS current
			DESCRIPTION
				"A table containing the list of led information."
			::= { swi4 2003 }
		
 		swi4FruLedEntry OBJECT-TYPE
			SYNTAX Swi4FruLedEntry
			MAX-ACCESS not-accessible
			STATUS current
			DESCRIPTION
				"Information about a particular current led."
			INDEX { swi4FruID, swi4FruLed }
			::= { swi4FruLedTable 1 }
		
		Swi4FruLedEntry ::=
			SEQUENCE { 
				swi4FruID
					INTEGER,
				swi4FruLed
					DisplayString,
				swi4FruLedColorProps
					DisplayString,
				swi4FruLedState
					DisplayString
			 }

 		swi4FruID OBJECT-TYPE
			SYNTAX INTEGER
			MAX-ACCESS not-accessible
			STATUS current
			DESCRIPTION
				"Fru ID"
			::= { swi4FruLedEntry 1 }
		
 		swi4FruLed OBJECT-TYPE
			SYNTAX DisplayString
			MAX-ACCESS not-accessible
			STATUS current
			DESCRIPTION
				"The current FRU indicator name."
			::= { swi4FruLedEntry 2 }
		
 		swi4FruLedColorProps OBJECT-TYPE
			SYNTAX DisplayString
			MAX-ACCESS read-only
			STATUS current
			DESCRIPTION
				"Finds out what colors are supported by the LED"
			::= { swi4FruLedEntry 3 }
		
 		swi4FruLedState OBJECT-TYPE
			SYNTAX DisplayString
			MAX-ACCESS read-write
			STATUS current
			DESCRIPTION
				"Get/Set the FRU LED state
				when set,there are five kinds of states can be set
				Settable value:
				            normal mode:            -  [localcontrol]
				            test mode:              -  [lamptest],[duration],[color]
				            blink mode:             -  [blink],[offtime],[ontime],[color]
				            turn on:                -  [on],[color]
				            turn off:               -  [off]"
			::= { swi4FruLedEntry 4 }
		
 		swi4FruDescriptionTable OBJECT-TYPE
			SYNTAX SEQUENCE OF Swi4FruDescriptionEntry
			MAX-ACCESS not-accessible
			STATUS current
			DESCRIPTION
				"A table containing the list of swi4 FRU information."
			::= { swi4 2004 }
		
 		swi4FruDescriptionEntry OBJECT-TYPE
			SYNTAX Swi4FruDescriptionEntry
			MAX-ACCESS not-accessible
			STATUS current
			DESCRIPTION
				"Information about a particular current FRU."
			INDEX { swi4fruNum }
			::= { swi4FruDescriptionTable 1 }
		
		Swi4FruDescriptionEntry ::=
			SEQUENCE { 
				swi4fruNum
					INTEGER,
				swi4fruBoardDescription
					DisplayString,
				swi4fruBoardManufacturer
					DisplayString,
				swi4fruBoardPartNumber
					DisplayString,
				swi4fruBoardSerialNumber
					DisplayString,
				swi4fruBoardManufactureDate
					DisplayString,
				swi4fruProductDescription
					DisplayString,
				swi4fruProductManufacturer
					DisplayString,
				swi4fruProductPartNumber
					DisplayString,
				swi4fruProductSerialNumber
					DisplayString,
				swi4fruProductRevision
					DisplayString,
				swi4fruAll
					DisplayString
			 }

 		swi4fruNum OBJECT-TYPE
			SYNTAX INTEGER
			MAX-ACCESS not-accessible
			STATUS current
			DESCRIPTION
				"swi4 FRU's INDEX"
			::= { swi4FruDescriptionEntry 1 }
		
 		swi4fruBoardDescription OBJECT-TYPE
			SYNTAX DisplayString
			MAX-ACCESS read-only
			STATUS current
			DESCRIPTION
				"Used to read the Board Description from the swi4 fru."
			::= { swi4FruDescriptionEntry 2 }
		
 		swi4fruBoardManufacturer OBJECT-TYPE
			SYNTAX DisplayString
			MAX-ACCESS read-only
			STATUS current
			DESCRIPTION
				"Used to read the Board Manufacturer from the swi4 fru."
			::= { swi4FruDescriptionEntry 3 }
		
 		swi4fruBoardPartNumber OBJECT-TYPE
			SYNTAX DisplayString
			MAX-ACCESS read-only
			STATUS current
			DESCRIPTION
				"Used to read the Board Part Number from the swi4 fru."
			::= { swi4FruDescriptionEntry 4 }
		
 		swi4fruBoardSerialNumber OBJECT-TYPE
			SYNTAX DisplayString
			MAX-ACCESS read-only
			STATUS current
			DESCRIPTION
				"Used to read the Board Serial Number from the swi4 fru."
			::= { swi4FruDescriptionEntry 5 }
		
 		swi4fruBoardManufactureDate OBJECT-TYPE
			SYNTAX DisplayString
			MAX-ACCESS read-only
			STATUS current
			DESCRIPTION
				"Used to read the Board Manufacture Date from the swi4 fru."
			::= { swi4FruDescriptionEntry 6 }
		
 		swi4fruProductDescription OBJECT-TYPE
			SYNTAX DisplayString
			MAX-ACCESS read-only
			STATUS current
			DESCRIPTION
				"Used to read the Product Description from the swi4 fru."
			::= { swi4FruDescriptionEntry 7 }
		
 		swi4fruProductManufacturer OBJECT-TYPE
			SYNTAX DisplayString
			MAX-ACCESS read-only
			STATUS current
			DESCRIPTION
				"Used to read the Product Manufacturer from the swi4 fru."
			::= { swi4FruDescriptionEntry 8 }
		
 		swi4fruProductPartNumber OBJECT-TYPE
			SYNTAX DisplayString
			MAX-ACCESS read-only
			STATUS current
			DESCRIPTION
				"Used to read the Product Part Number from the swi4 fru."
			::= { swi4FruDescriptionEntry 9 }
		
 		swi4fruProductSerialNumber OBJECT-TYPE
			SYNTAX DisplayString
			MAX-ACCESS read-only
			STATUS current
			DESCRIPTION
				"Used to read the Product Serial Number from the swi4 fru."
			::= { swi4FruDescriptionEntry 10 }
		
 		swi4fruProductRevision OBJECT-TYPE
			SYNTAX DisplayString
			MAX-ACCESS read-only
			STATUS current
			DESCRIPTION
				"Used to read the Product Revision from the swi4 fru."
			::= { swi4FruDescriptionEntry 13 }
		
 		swi4fruAll OBJECT-TYPE
			SYNTAX DisplayString
			MAX-ACCESS read-only
			STATUS current
			DESCRIPTION
				"Used to read the fru info all."
			::= { swi4FruDescriptionEntry 14 }
		
 		swi4PortTargetTable OBJECT-TYPE
			SYNTAX SEQUENCE OF Swi4PortTargetEntry
			MAX-ACCESS not-accessible
			STATUS current
			DESCRIPTION
				"A table containing the list of sensor information."
			::= { swi4 2005 }
		
 		swi4PortTargetEntry OBJECT-TYPE
			SYNTAX Swi4PortTargetEntry
			MAX-ACCESS not-accessible
			STATUS current
			DESCRIPTION
				"Information about a particular current sensor."
			INDEX { swi1PortNum }
			::= { swi4PortTargetTable 1 }
		
		Swi4PortTargetEntry ::=
			SEQUENCE { 
				swi4PortNum
					INTEGER,
				swi4OTMState
					INTEGER,
				swi4OTMInfo
					DisplayString,
				swi4PhyState
					INTEGER,
				swi4PhyReset
					INTEGER,
				swi4PortToBladeSlot
					INTEGER,
				swi4PortName
					DisplayString,
				swi4OTMData
					DisplayString,
				swi4PortState
					INTEGER		
			 }

 		swi4PortNum OBJECT-TYPE
			SYNTAX INTEGER
			MAX-ACCESS read-only
			STATUS current
			DESCRIPTION
				"Port Num"
			::= { swi4PortTargetEntry 1 }
		
 		swi4OTMState OBJECT-TYPE
			SYNTAX INTEGER
				{
				not-present(0),
				present(1)
				}
			MAX-ACCESS read-only
			STATUS current
			DESCRIPTION
				"Used to get the optical module status. 
				This will be one of the following:
				(0-not present, 1-present)"
			::= { swi4PortTargetEntry 2 }
		
 		swi4OTMInfo OBJECT-TYPE
			SYNTAX DisplayString
			MAX-ACCESS read-only
			STATUS current
			DESCRIPTION
				"Used to get the optical module information."
			::= { swi4PortTargetEntry 3 }
		
 		swi4PhyState OBJECT-TYPE
			SYNTAX INTEGER
				{
				down(0),
				up(1)
				}
			MAX-ACCESS read-only
			STATUS current
			DESCRIPTION
				"Phy state"
			::= { swi4PortTargetEntry 4 }
		
 		swi4PhyReset OBJECT-TYPE
			SYNTAX INTEGER
			MAX-ACCESS write-only
			STATUS current
			DESCRIPTION
				"Phy reset"
			::= { swi4PortTargetEntry 5 }
		
 		swi4PortToBladeSlot OBJECT-TYPE
			SYNTAX INTEGER
			MAX-ACCESS read-only
			STATUS current
			DESCRIPTION
				"Used to get the server slot number."
			::= { swi4PortTargetEntry 6 }
		
 		swi4PortName OBJECT-TYPE
			SYNTAX DisplayString
			MAX-ACCESS read-only
			STATUS current
			DESCRIPTION
				"Port name"
			::= { swi4PortTargetEntry 7 }
		
		swi4OTMData OBJECT-TYPE
			SYNTAX DisplayString
			MAX-ACCESS read-only
			STATUS current
			DESCRIPTION
				"Used to get the optical module real time data."
			::= { swi4PortTargetEntry 8 }
			
		swi4PortState OBJECT-TYPE
			SYNTAX INTEGER
				{
				linkUp(1),
				phyLinkDown(2),
				phyLinkUp(3),
				linkFault(4), 
				invalidState(255)
				}
			MAX-ACCESS read-only
			STATUS current
			DESCRIPTION
				"Port state"
			::= { swi4PortTargetEntry 9 }	

 		bladeshealthevents OBJECT IDENTIFIER ::= { hwSMM 55 }
		
 		bladeshealtheventsTable OBJECT-TYPE
			SYNTAX SEQUENCE OF BladeshealtheventsEntry
			MAX-ACCESS not-accessible
			STATUS current
			DESCRIPTION
				"A table containing the list of led information."
			::= { bladeshealthevents 2001 }
		
 		bladeshealtheventsEntry OBJECT-TYPE
			SYNTAX BladeshealtheventsEntry
			MAX-ACCESS not-accessible
			STATUS current
			DESCRIPTION
				"Information about a particular current led."
			INDEX { bladeNameIndex, bladeeventIndex }
			::= { bladeshealtheventsTable 1 }
		
		BladeshealtheventsEntry ::=
			SEQUENCE { 
				bladeNameIndex
					DisplayString,
				bladeeventIndex
					INTEGER,
				bladehealthEvents
					DisplayString
			 }

 		bladeNameIndex OBJECT-TYPE
			SYNTAX DisplayString
			MAX-ACCESS not-accessible
			STATUS current
			DESCRIPTION
				" "
			::= { bladeshealtheventsEntry 1 }
		
 		bladeeventIndex OBJECT-TYPE
			SYNTAX INTEGER
			MAX-ACCESS not-accessible
			STATUS current
			DESCRIPTION
				" "
			::= { bladeshealtheventsEntry 2 }
		
 		bladehealthEvents OBJECT-TYPE
			SYNTAX DisplayString
			MAX-ACCESS read-only
			STATUS current
			DESCRIPTION
				" "
			::= { bladeshealtheventsEntry 3 }
		
		hwTrap OBJECT IDENTIFIER ::= { hwSMM 500 }
		
		hwTrapVar OBJECT IDENTIFIER ::= { hwTrap 1 }
		
		hwTrapSeq OBJECT-TYPE
			SYNTAX INTEGER
			MAX-ACCESS read-only
			STATUS current
			DESCRIPTION
				"Trap sequence"
			::= { hwTrapVar 1 }
		
		hwTrapSensorName OBJECT-TYPE
			SYNTAX DisplayString
			MAX-ACCESS read-only
			STATUS current
			DESCRIPTION
				"Trap sensor name"
			::= { hwTrapVar 2 }
		
		hwTrapEvent OBJECT-TYPE
			SYNTAX DisplayString
			MAX-ACCESS read-only
			STATUS current
			DESCRIPTION
				"Trap description "
			::= { hwTrapVar 3 }
		
		hwTrapSeverity OBJECT-TYPE
			SYNTAX INTEGER
			MAX-ACCESS read-only
			STATUS current
			DESCRIPTION
				"Trap severity"
			::= { hwTrapVar 4 }
		
		hwTrapEventCode OBJECT-TYPE
			SYNTAX DisplayString
			MAX-ACCESS read-only
			STATUS current
			DESCRIPTION
				"Trap EventCode"
			::= { hwTrapVar 5 }
		
		hwTrapEventData2 OBJECT-TYPE
			SYNTAX INTEGER
			MAX-ACCESS read-only
			STATUS current
			DESCRIPTION
				"Trap Event Data 2"
			::= { hwTrapVar 6 }
		
		hwTrapEventData3 OBJECT-TYPE
			SYNTAX INTEGER
			MAX-ACCESS read-only
			STATUS current
			DESCRIPTION
				"Trap Event Data 3"
			::= { hwTrapVar 7 }
		
		hwTrapBlade OBJECT-TYPE
			SYNTAX DisplayString
			MAX-ACCESS read-only
			STATUS current
			DESCRIPTION
				"Trap blade name"
			::= { hwTrapVar 8 }
		
		hwTrapChassisSerial OBJECT-TYPE
			SYNTAX INTEGER
			MAX-ACCESS read-only
			STATUS current
			DESCRIPTION
				"Trap chassis serial"
			::= { hwTrapVar 9 }
		
		hwTrapEventTime OBJECT-TYPE
			SYNTAX DisplayString
			MAX-ACCESS read-only
			STATUS current
			DESCRIPTION
				"Trap Event Time"
			::= { hwTrapVar 10 }
		
		hwTRAPObject OBJECT IDENTIFIER ::= { hwTrap 10 }
		
		hwCPU OBJECT IDENTIFIER ::= { hwTRAPObject 7 }
		
		hwCPUCATError NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 1 }
		
		hwCPUCATErrorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 2 }
		
		hwCPUThermalTrip NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 17 }
		
		hwCPUThermalTripDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 18 }
		
		hwCPUSelfTestFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 33 }
		
		hwCPUSelfTestFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 34 }
		
		hwCPUCfgError NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 81 }
		
		hwCPUCfgErrorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 82 }
		
		hwCPUPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 113 }
		
		hwCPUPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 114 }
		
		hwCPUDisable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 129 }
		
		hwCPUDisableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 130 }
		
		hwCPUMCE NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 177 }
		
		hwCPUMCEDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 178 }
		
		hwCPUCorrectableMachineCheckErr NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 193 }
		
		hwCPUCorrectableMachineCheckErrDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPU 194 }
		
		hwPowerSupply OBJECT IDENTIFIER ::= { hwTRAPObject 8 }
		
		hwPowerSupplyFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPowerSupply 17 }
		
		hwPowerSupplyFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPowerSupply 18 }
		
		hwMemory OBJECT IDENTIFIER ::= { hwTRAPObject 12 }
		
		hwCorrectableECC NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 1 }
		
		hwCorrectableECCDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 2 }
		
		hwUncorrectableECC NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 17 }
		
		hwUncorrectableECCDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 18 }
		
		hwMemoryECCLimitation NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 81 }
		
		hwMemoryECCLimitationDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 82 }
		
		hwMemoryPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 97 }
		
		hwMemoryPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 98 }
		
		hwMemoryCfgError NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 113 }
		
		hwMemoryCfgErrorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 114 }
		
		hwMemorySpare NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 129 }
		
		hwMemorySpareDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 130 }
		
		hwMemoryOvertemp NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 161 }
		
		hwMemoryOvertempDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemory 162 }
		
		hwHardDisk OBJECT IDENTIFIER ::= { hwTRAPObject 13 }
		
		hwHardDiskPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 1 }
		
		hwHardDiskPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 2 }
		
		hwHardDiskFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 17 }
		
		hwHardDiskFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 18 }
		
		hwRAIDArrayFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 97 }
		
		hwRAIDArrayFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHardDisk 98 }
		
		hwSysFwProgress OBJECT IDENTIFIER ::= { hwTRAPObject 15 }
		
		hwSystemFirmwareHang NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 17 }
		
		hwSystemFirmwareHangDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 18 }
		
		hwVideoControllerFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 2305 }
		
		hwVideoControllerFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 2306 }
		
		hwCPUVoltageMismatch NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 3073 }
		
		hwCPUVoltageMismatchDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysFwProgress 3074 }
			
		hwLogspaStatus OBJECT IDENTIFIER ::= { hwTRAPObject 16 }
		
		hwLogspaStatusFull NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLogspaStatus 65 }
		
		hwLogspaStatusFullDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLogspaStatus 66 }
		
		
		hwSysEvent OBJECT IDENTIFIER ::= { hwTRAPObject 18 }
		
		hwSysEventInstance NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysEvent 65 }
		
		hwPowerButton OBJECT IDENTIFIER ::= { hwTRAPObject 20 }
		
		hwPowerButtonPressed NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPowerButton 1 }
		
		hwCableInterconnectStatus OBJECT IDENTIFIER ::= { hwTRAPObject 27 }
		
		hwCableInterconnectConfigErr NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCableInterconnectStatus 17 }
		
		hwCableInterconnectConfigErrDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCableInterconnectStatus 18 }
		
		hwSysRestart OBJECT IDENTIFIER ::= { hwTRAPObject 29 }
		
		hwSysRestartUnknown NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 113 }
		
		hwSysRestartChassisCtrl NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 369 }
		
		hwSysRestartPowerButton NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 881 }
		
		hwSysRestartWatchdogCtrl NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 1137 }
		
		hwSysRestartAlwaysRestore NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 1649 }
		
		hwSysRestartRestorePrevState NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwSysRestart 1905 }
		
		hwBootError OBJECT IDENTIFIER ::= { hwTRAPObject 30 }
		
		hwNoBootableMedia NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 1 }
		
		hwNoBootableMediaDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 2 }
		
		hwNoBootableDisk NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 17 }
		
		hwNoBootableDiskDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 18 }
		
		hwPXENotFound NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 33 }
		
		hwPXENotFoundDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 34 }
		
		hwInvalidBootSector NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 49 }
		
		hwInvalidBootSectorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBootError 50 }
		
		hwDeviceFault OBJECT IDENTIFIER ::= { hwTRAPObject 33 }
		
		hwHardwareDeviceFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 1 }
		
		hwHardwareDeviceFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 2 }
		
		hwPhyPortFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 17 }
		
		hwPhyPortFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 18 }
		
		hwPCIeFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 2305 }
		
		hwPCIeFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 2306 }
		
		hwHardwareAddrFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 57857 }
		
		hwHardwareAddrFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwDeviceFault 57858 }
		
		hwACPIStatus OBJECT IDENTIFIER ::= { hwTRAPObject 34 }
		
		hwACPIStatusS0 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwACPIStatus 1 }
		
		hwACPIStatusS4S5 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwACPIStatus 97 }
		
		hwWatchDog OBJECT IDENTIFIER ::= { hwTRAPObject 35 }
		
		hwWatchDogOverflow NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 1 }
		
		hwWatchDogOverflowDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 2 }
		
		hwWatchDogReset NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 17 }
		
		hwWatchDogResetDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 18 }
		
		hwWatchDogPowerDown NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 33 }
		
		hwWatchDogPowerDownDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 34 }
		
		hwWatchDogPowerCycle NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 49 }
		
		hwWatchDogPowerCycleDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwWatchDog 50 }
		
		hwLANHeartBeat OBJECT IDENTIFIER ::= { hwTRAPObject 39 }
		
		hwLANHeartLost NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLANHeartBeat 1 }
		
		hwLANHeartLostDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLANHeartBeat 2 }
            
--		hwLANHeartBeat NOTIFICATION-TYPE
--			OBJECTS { hwTrapSeq, hwTrapSensorName, hwTrapEvent, hwTrapEventCode, hwTrapEventData2, 
--				hwTrapEventData3, hwTrapBlade, hwTrapChassisSerial, hwTrapEventTime }
--			STATUS current
--			DESCRIPTION 
--				"LAN heartbeat lost, Assertion"
--			::= { hwLANHeartBeat 17 }
		
--		hwLANHeartBeatDeassert NOTIFICATION-TYPE
--			OBJECTS { hwTrapSeq, hwTrapSensorName, hwTrapEvent, hwTrapEventCode, hwTrapEventData2, 
--				hwTrapEventData3, hwTrapBlade, hwTrapChassisSerial, hwTrapEventTime }
--			STATUS current
--			DESCRIPTION 
--				"LAN heartbeat lost, Deassertion"
--			::= { hwLANHeartBeat 18 }
		
		hwMngmntHealth OBJECT IDENTIFIER ::= { hwTRAPObject 40 }
		
		hwSensorAccessibleFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 1 }
		
		hwSensorAccessibleFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 2 }
		
		hwControllerAccessibleFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 17 }
		
		hwControllerAccessibleFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 18 }
		
		hwManagmentControllerUnaccessible NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 49 }
		
		hwManagmentControllerUnaccessibleDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 50 }
		
		hwFruFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 81 }
		
		hwFruFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMngmntHealth 82 }
		
		hwBattery OBJECT IDENTIFIER ::= { hwTRAPObject 41 }
		
		hwRTCBatterylow NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBattery 1 }
		
		hwRTCBatterylowDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwBattery 2 }
		
		hwVersionChangeStatus OBJECT IDENTIFIER ::= { hwTRAPObject 43 }
		
		hwVersionChange NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwVersionChangeStatus 17 }
		
		hwHardwareIncompatibility NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwVersionChangeStatus 33 }
		
		hwHardwareIncompatibilityDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwVersionChangeStatus 34 }
		
		hwFirmwareIncompatibility NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"The firmware version is different from the other smm."
			::= { hwVersionChangeStatus 49 }
		
		hwFirmwareIncompatibilityDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"The firmware version is the same with the other smm."
			::= { hwVersionChangeStatus 50 }
			
		hwFruStatus OBJECT IDENTIFIER ::= { hwTRAPObject 44 }
		
		hwFruInactive NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFruStatus 17 }
		
		hwFruInactiveDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFruStatus 18 }
		
		hwI2cStatus OBJECT IDENTIFIER ::= { hwTRAPObject 211 }
		
		hwI2cNoFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 1 }
		
		hwI2cClockDriveHiUnable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 17 }
		
		hwI2cClockDriveHiUnableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 18 }
		
		hwI2cDataDriveHiUnable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 33 }
		
		hwI2cDataDriveHiUnableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 34 }
		
		hwI2cClockDriveLoUnable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 49 }
		
		hwI2cClockDriveLoUnableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 50 }
		
		hwI2cDataDriveLoUnable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 65 }
		
		hwI2cDataDriveLoUnableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 66 }
		
		hwI2cAccessFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 81 }
		
		hwI2cAccessFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwI2cStatus 82 }
		
		hwHotSwap OBJECT IDENTIFIER ::= { hwTRAPObject 240 }
		
		hwHotSwaptoM0 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 1 }
		
		hwHotSwaptoM1 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 17 }
		
		hwHotSwaptoM2 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 33 }
		
		hwHotSwaptoM3 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 49 }
		
		hwHotSwaptoM4 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 65 }
		
		hwHotSwaptoM5 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 81 }
		
		hwHotSwaptoM6 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 97 }
		
		hwHotSwaptoM7 NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwHotSwap 113 }
            
        hwHotSwaptoM7Deassert NOTIFICATION-TYPE
            OBJECTS { hwTrapSeq, hwTrapSensorName, hwTrapEvent, hwTrapEventCode, hwTrapEventData2, 
                hwTrapEventData3, hwTrapBlade, hwTrapChassisSerial, hwTrapEventTime }
            STATUS current
            DESCRIPTION 
                "Transition to M7, Deassertion"
            ::= { hwHotSwap 114 }
		
		hwOvertemperature OBJECT IDENTIFIER ::= { hwTRAPObject 257 }
		
		hwTempLoMinor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 1 }
		
		hwTempLoMinorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 2 }
		
		hwTempLoMajor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 33 }
		
		hwTempLoMajorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 34 }
		
		hwTempHiMinor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 113 }
		
		hwTempHiMinorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 114 }
		
		hwTempHiMajor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 145 }
		
		hwTempHiMajorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 146 }
		
		hwTempHiCritical NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 177 }
		
		hwTempHiCriticalDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOvertemperature 178 }
		
		hwOverVoltage OBJECT IDENTIFIER ::= { hwTRAPObject 258 }
		
		hwVoltLoMinor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 1 }
		
		hwVoltLoMinorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 2 }
		
		hwVoltLoMajor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 33 }
		
		hwVoltLoMajorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 34 }
		
		hwVoltHiMinor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 113 }
		
		hwVoltHiMinorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 114 }
		
		hwVoltHiMajor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 145 }
		
		hwVoltHiMajorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 146 }
		
		hwVoltHiCritical NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 177 }
		
		hwVoltHiCriticalDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwOverVoltage 178 }
		
		hwMemoryRate OBJECT IDENTIFIER ::= { hwTRAPObject 268 }
		
		hwMemoryRateHiMinor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemoryRate 113 }
		
		hwMemoryRateHiMinorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwMemoryRate 114 }
		
		hwFlashUsage OBJECT IDENTIFIER ::= { hwTRAPObject 294 }
		
		hwFlashUsageHiMajor NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFlashUsage 145 }
		
		hwFlashUsageHiMajorDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFlashUsage 146 }
		
		hwFailOver OBJECT IDENTIFIER ::= { hwTRAPObject 530 }
		
		hwFailOverIdle NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFailOver 1 }
            
		hwFailOverIdleDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"FailOver, Deassertion"
			::= { hwFailOver 2 }
		
		hwCPURateStatus OBJECT IDENTIFIER ::= { hwTRAPObject 775 }
		
		hwCPURate NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPURateStatus 17 }
		
		hwCPURateDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCPURateStatus 18 }
		
		hwUIDButton OBJECT IDENTIFIER ::= { hwTRAPObject 788 }
		
		hwUIDButtonPressed NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwUIDButton 17 }
		
		hwPowerCapping OBJECT IDENTIFIER ::= { hwTRAPObject 1042 }
		
		hwPowerCapFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPowerCapping 17 }
		
		hwPowerCapFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPowerCapping 18 }
		
		hwCardFault OBJECT IDENTIFIER ::= { hwTRAPObject 1047 }
		
		hwCardStatusFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCardFault 17 }
		
		hwCardStatusFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCardFault 18 }
			
		hwCertExpireStatus OBJECT IDENTIFIER ::= { hwTRAPObject 1320 }

		hwLowPowerStatus OBJECT IDENTIFIER ::= { hwTRAPObject 1800 }

		
		hwLowPower NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLowPowerStatus 33 }

		
		hwLowPowerDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLowPowerStatus 34 }
		
		hwCertStatusExpiring NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCertExpireStatus 1 }
		
		hwCertStatusExpiringDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCertExpireStatus 2 }
		
		hwCertStatusExpired NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCertExpireStatus 17 }
		
		hwCertStatusExpiredDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCertExpireStatus 18 }
		
		hwFailoverngStatus OBJECT IDENTIFIER ::= { hwTRAPObject 1805 }
		hwFailoverng NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Assert when compute node transfer failed"
			::= { hwFailoverngStatus 33 }

		hwFailoverngDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Deassert when all except node removed"
			::= { hwFailoverngStatus 34 }

		
		hwLswFailStatus OBJECT IDENTIFIER ::= { hwTRAPObject 1825 }
		
		hwLswFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLswFailStatus 49 }
		
		hwLswFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwLswFailStatus 50 }
		
		hwPortManagementStatus OBJECT IDENTIFIER ::= { hwTRAPObject 1831 }
		
		hwPortManagementFail NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPortManagementStatus 33 }
		
		hwPortManagementFailDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPortManagementStatus 34 }
		
		hwFanFault OBJECT IDENTIFIER ::= { hwTRAPObject 1832 }
		
		hwFanStatusFault NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFanFault 17 }
		
		hwFanStatusFaultDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFanFault 18 }
		
		hwPSPresenceStatus OBJECT IDENTIFIER ::= { hwTRAPObject 2056 }
		
		hwPSRemoved NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Assert removal alarm when removal PSU"
			::= { hwPSPresenceStatus 1 }
		hwPSRemovedDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Deassert removal alarm when insert PSU"
			::= { hwPSPresenceStatus 2 }
		hwPSPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPSPresenceStatus 17 }
		
		hwPSPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwPSPresenceStatus 18 }
		
		hwFanPresenceStatus OBJECT IDENTIFIER ::= { hwTRAPObject 2058 }
		
		hwFanRemoved NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Assert removal alarm when removal fantray"
			::= { hwFanPresenceStatus 1 }
		hwFanRemovedDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Deassert removal alarm when insert fantray"
			::= { hwFanPresenceStatus 2 }
		hwFanPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFanPresenceStatus 17 }
		
		hwFanPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwFanPresenceStatus 18 }
		
		hwCardPresenceStatus OBJECT IDENTIFIER ::= { hwTRAPObject 2071 }
		
		hwCardPresence NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCardPresenceStatus 17 }
		
		hwCardPresenceDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwCardPresenceStatus 18 }
		
		hwRemovedAlarmStatus OBJECT IDENTIFIER ::= { hwTRAPObject 2081 }
		hwRemovedAlarm NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Assert removal alarm when removal compute node,switch or passthrough module,MM910 management module"
			::= { hwRemovedAlarmStatus 1 }
		hwRemovedAlarmDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				"Deassert removal alarm when insert compute node,switch or passthrough module,MM910 management module"
			::= { hwRemovedAlarmStatus 2 }
		hwProcessorEnableStatus OBJECT IDENTIFIER ::= { hwTRAPObject 2311 }
		
		hwProcessorDisable NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwProcessorEnableStatus 1 }
		
		hwProcessorDisableDeassert NOTIFICATION-TYPE
			OBJECTS { hwTrapSeq, hwTrapSensorName, hwTrapEvent, hwTrapEventCode, hwTrapEventData2, 
				hwTrapEventData3, hwTrapBlade, hwTrapChassisSerial, hwTrapEventTime }
			STATUS current
			DESCRIPTION 
				" "
			::= { hwProcessorEnableStatus 2 }
	
	END

--
-- HWSMM-MIB.my
--
