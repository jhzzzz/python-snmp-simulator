--/****************************************************************************
--
--  Copyright (C), 2011-2016, Huawei Tech. Co., Ltd.
--
--*****************************************************************************
--  File Name     : HUAWEI-SERVER-IBMC-MIB.mib
--
--****************************************************************************/

HUAWEI-SERVER-IBMC-MIB DEFINITIONS ::= BEGIN
	IMPORTS    MODULE-IDENTITY, OBJECT-TYPE, NOTIFICATION-TYPE,Integer32
                   FROM SNMPv2-SMI
               Counter32,
               IpAddress,
               Gauge32,
               Unsigned32,
               TimeTicks,
               Opaque,
               Counter64
                   FROM SNMPv2-SMI
               RowStatus,
               StorageType
                   FROM SNMPv2-TC
               SnmpAdminString
                   FROM SNMP-FRAMEWORK-MIB
               enterprises
                   FROM SNMPv2-SMI 
               DisplayString
    			   FROM RFC1213-MIB;

        huawei OBJECT IDENTIFIER ::= { enterprises 2011 } 
        products OBJECT IDENTIFIER ::= { huawei 2 }
        hwServer OBJECT IDENTIFIER ::={ products 235 }
        hwBMC OBJECT IDENTIFIER ::={ hwServer 1 }        
       
        hwiBMC MODULE-IDENTITY
              LAST-UPDATED 	"201110250000Z"  
              ORGANIZATION 	"Huawei Technologies Co.,Ltd."
              CONTACT-INFO
              				" http://www.huawei.com
                   	          Zip:518129   E-mail:support@huawei.com "    
              DESCRIPTION
                            "The HUAWEI-SERVER-IBMC-MIB contains objects to Manage the server."
              ::= { hwBMC 1 }

--    ****** uspSystem Location ******************************* 
		system OBJECT IDENTIFIER ::= { hwiBMC 1 }


		systemHealth OBJECT-TYPE
			SYNTAX INTEGER
				{
				ok(1),
				minor(2),
				major(3), 
				critical(4)
				}
			MAX-ACCESS read-only
			STATUS current
			DESCRIPTION
				"systemHealth information about system present state of health. 
				This value will be one of the following:
				(1-OK, 2-Minor, 3-Major, 4-Critical)"
			::= { system 1 }


		systemBootsequence OBJECT-TYPE
			SYNTAX INTEGER
				{
				noOverride(1),
				pxe(2),				
				hdd(3),
				cdDvd(4),
				floppyPrimaryRemovableMedia(5),
				unspecified(6),
				biossetup(7)
				}
			MAX-ACCESS read-write
			STATUS current
			DESCRIPTION
				"Decide the system's first boot device.
				 1  - No override
				 2  - Force PXE
				 3  - Force boot from default Hard-drive
				 4  - Force boot from default CD/DVD
				 5  - Force boot from Floppy/primary removable media
				 6  - boot flags valid. The bit should be set to indicate that valid flag data is present. 
					  This bit may be automatically cleared based on the boot flag valid bit clearing 
					  parameter, above.(This option is read-only.)
				 7 -  Force boot into BIOS SETUP
			     The default value is 6 (unspecified)"
			::= { system 2 }    


		systemTime OBJECT-TYPE
			SYNTAX DisplayString
			MAX-ACCESS read-only
			STATUS current
			DESCRIPTION
				"systemTime information about iBMC system time, based on UTC.
				the value such as (yyyy-mm-dd hh:mm:ss)."
			::= { system 3 }  


		systemTimeZone OBJECT-TYPE
			SYNTAX Integer32 (-720..780)
			MAX-ACCESS read-write
			STATUS current
			DESCRIPTION
				"systemTimeZone information about iBMC time zone.
				The value is in [-720, 780]."
			::= { system 4 }	
        

		safepowerofftime OBJECT-TYPE
			SYNTAX Integer32
			MAX-ACCESS read-write
			STATUS current
			DESCRIPTION
				"The system safe poweroff time, the value 0 indicates non-timeout."
			::= { system 5 }   
			   

		deviceName OBJECT-TYPE
			SYNTAX DisplayString
			MAX-ACCESS read-only
			STATUS current
			DESCRIPTION
				"The device name value between 1 to 63 characters."
			::= { system 6 } 
			

		deviceSerialNo OBJECT-TYPE
			SYNTAX DisplayString
			MAX-ACCESS read-only
			STATUS current
			DESCRIPTION
				"The device serial number value between 1 to 63 characters."
			::= { system 7 }   
			


		powerOnPolicy OBJECT-TYPE
			SYNTAX INTEGER
				{
				stayoff(1),
				restorePreviousState(2),				
				turnon(3)
				}
			MAX-ACCESS read-write
			STATUS current
			DESCRIPTION
				"1  - Stay Off
				 2  - Restore Previous State
				 3  - Turn On
				 Default value is turnon(3)."
			::= { system 8 }  	


		hostName OBJECT-TYPE
			SYNTAX DisplayString
			MAX-ACCESS read-write
			STATUS current
			DESCRIPTION
				"The host name between 1 to 64 characters.
				Supported characters: 0-9 a-z A-Z - ('-' is not allowed to be the first/last character).
				Default value is huawei."
			::= { system 9 } 			
					           

		systemGuid OBJECT-TYPE
			SYNTAX DisplayString
			MAX-ACCESS read-only
			STATUS current
			DESCRIPTION
				"The GUID is hex string such as 
				********-****-****-****-************."
			::= { system 10 }  
			

		identify OBJECT-TYPE   
			SYNTAX DisplayString
			MAX-ACCESS read-write
			STATUS current
			DESCRIPTION
				"identify use to control on or off of led. 
				 identify mode:   
				 0  - Off	
				 1  - Temporary On	
				 2  - Force Identify On	             
				 
				 set format: <mode>,[ontime]
				 get format: <mode>   
				 
				 When <mode> = 0 or <mode> = 2,
				 the format is only <mode>.
				    
				 [ontime] is option and value is in [1,255],
				 When set Temporary On without [ontime],
				 The default Temporary On time are 15 seconds."
			::= { system 11 }
								

		systemPowerState OBJECT-TYPE   
			SYNTAX INTEGER
				{
				normalPowerOff(1),
				powerOn(2),				
				forcedSystemReset(3),
				forcedPowerCycle(4),
				forcedPowerOff(5)
				}
			MAX-ACCESS read-write
			STATUS current
			DESCRIPTION
				"System Power Status Get.
				1  - Power Off
				2  - Power On
				System Power Status Set.
				1  - Normal Power Off
				2  - Power On
				3  - Forced System Reset
				4  - Forced Power Cycle
				5  - Forced Power Off
				The set actions are a process which will take effect in a while. 
				When system in poweroff state, Power Off/Reset/PowerOffThenOn commonds are not supported."
			::= { system 12 }
		

		presentSystemPower OBJECT-TYPE
			SYNTAX INTEGER
			MAX-ACCESS read-only
			STATUS current
			DESCRIPTION
				"Display the present system power."
			::= { system 13 } 	 

		deviceOwnerID OBJECT-TYPE
			SYNTAX DisplayString
			MAX-ACCESS read-only
			STATUS current
			DESCRIPTION
				"The device owner ID, maxlength  is 64 characters."
			::= { system 14 } 
		
		deviceslotID OBJECT-TYPE
			SYNTAX DisplayString
			MAX-ACCESS read-only
			STATUS current
			DESCRIPTION
				"The device slot ID of a server exists, the value ranges from 1 to 80. Otherwise, the value is 0."
			::= { system 15 } 
			
		remoteOEMInfo OBJECT-TYPE
			SYNTAX DisplayString
			MAX-ACCESS read-write
			STATUS current
			DESCRIPTION
				"The remoteOEMinfo, maxlength  is 255 characters."
			::= { system 16 } 			
			
		deviceLocationInfo OBJECT-TYPE
			SYNTAX DisplayString
			MAX-ACCESS read-write
			STATUS current
			DESCRIPTION
				"The deviceLocationInfo between 0 and 64 characters.
				Default value is server room."
			::= { system 17 }
		
		deviceRemoteManageID OBJECT-TYPE
			SYNTAX DisplayString
			MAX-ACCESS read-write
			STATUS current
			DESCRIPTION
				"The deviceRemoteManageID between 0 and 64 characters."
			::= { system 18 }			
			
		bmcReboot OBJECT-TYPE
			SYNTAX INTEGER
			        {
			        reboot(1)
			        }			   
			MAX-ACCESS read-write
			STATUS current
			DESCRIPTION
				"Reboot the BMC management system.When set, the value is only 1, write only."
			::= { system 19 }			
			
		powerOnPermit OBJECT-TYPE
			SYNTAX INTEGER
			{
				notPermit(1),
				permit(2)
			}
			MAX-ACCESS read-write
			STATUS current
			DESCRIPTION
				"Set power on permission. notPermit 1, permit 2."
			::= { system 20 }
			
		autoDiscoveryEnable OBJECT-TYPE
			SYNTAX INTEGER
			{
				disable(1),
				enable(2)
			}
			MAX-ACCESS read-write
			STATUS current
			DESCRIPTION
				"Auto discovery state. disable 1, enable 2.
				Default value is disable(1)."
			::= { system 21 }
		
		productUniqueID OBJECT-TYPE
			SYNTAX DisplayString
			MAX-ACCESS read-only
			STATUS current
			DESCRIPTION
				"The productUniqueID is hex string."
			::= { system 22 }
		systemCpuUsage OBJECT-TYPE
			SYNTAX INTEGER
			MAX-ACCESS read-only
			STATUS current
			DESCRIPTION
				"Percent of CPU usage.
				This value is in [0,100]."
			::= { system 23 }
			
		systemBootOnce OBJECT-TYPE
			SYNTAX INTEGER
			{
				once(1),
				permanent(2)
			}
			MAX-ACCESS read-write
			STATUS current
			DESCRIPTION
			"System boot once or permanent. once 1, permanent 2.
			Default value is once(1)."
			::= { system 24 }
			
--    ****** systemHealthEvent Information *******************************
  
--	  systemHealthEvent OBJECT IDENTIFIER ::= { system 30 }    

		systemHealthEventDescriptionTable OBJECT-TYPE
			SYNTAX SEQUENCE OF SystemHealthEventDescriptionEntry 
			MAX-ACCESS not-accessible
			STATUS current
			DESCRIPTION
				"A table containing the part component."
			::= { system 50 }
        
                systemHealthEventDescriptionEntry OBJECT-TYPE
			SYNTAX SystemHealthEventDescriptionEntry 
			MAX-ACCESS not-accessible
			STATUS current
			DESCRIPTION
				"."
			INDEX { eventIndex }
			::= { systemHealthEventDescriptionTable 1 }
		
		SystemHealthEventDescriptionEntry ::=
			SEQUENCE {
				eventIndex
					INTEGER, 
				eventSensorName
					DisplayString,
				eventAlertTime
					DisplayString,
				eventAlertSeverity
					INTEGER,	
				eventDescription 
					DisplayString
					}
				 

		eventIndex OBJECT-TYPE	
			SYNTAX INTEGER
			MAX-ACCESS not-accessible
			STATUS current
			DESCRIPTION
				"Information about event id."
			::= { systemHealthEventDescriptionEntry 1 }    
			

		eventSensorName OBJECT-TYPE
			SYNTAX DisplayString
			MAX-ACCESS read-only
			STATUS current
			DESCRIPTION
				"The sensor name between 1 to 16 characters."
			::= { systemHealthEventDescriptionEntry 2 }
			

		eventAlertTime OBJECT-TYPE
			SYNTAX DisplayString
			MAX-ACCESS read-only
			STATUS current
			DESCRIPTION
				"The format of alert time is yyyy-mm-dd hh:mm:ss, based on UTC."
			::= { systemHealthEventDescriptionEntry 3 }


		eventAlertSeverity OBJECT-TYPE
			SYNTAX INTEGER
				{
				ok(1),
				minor(2),
				major(3),
				critical(4)
				}
			MAX-ACCESS read-only
			STATUS current
			DESCRIPTION
				"The information about event level."
			::= { systemHealthEventDescriptionEntry 4 }     
			

		eventDescription OBJECT-TYPE
			SYNTAX DisplayString
			MAX-ACCESS read-only
			STATUS current
			DESCRIPTION
				"The event description between 1 to 255 characters."
			::= { systemHealthEventDescriptionEntry 5 }			 				
			
--    ****** DNS Location *******************************
  
		domainNameSystem OBJECT IDENTIFIER ::= { hwiBMC 2 }    


		domainName OBJECT-TYPE	
			SYNTAX DisplayString
			MAX-ACCESS read-write
			STATUS current
			DESCRIPTION
				"Domain Name between 0 to 67  characters.
				A domain name supports all characters except space,double quotation,equal and the following characters:#'&."
			::= { domainNameSystem 1 } 
			

		preferredDNSServer OBJECT-TYPE
			SYNTAX DisplayString
			MAX-ACCESS read-write
			STATUS current
			DESCRIPTION
				"Preferred DNS server IPv4 address.
				 this value is right IPv4 address or empty, 
				 the default value is empty."
			::= { domainNameSystem 2 }
			

		alternateDNSServer OBJECT-TYPE
			SYNTAX DisplayString
			MAX-ACCESS read-write
			STATUS current
			DESCRIPTION
				"Alternate DNS server IPv4 address.
				 this value is right IPv4 address or empty, 
				 the default value is empty."
			::= { domainNameSystem 3 }
			

		dnsSource OBJECT-TYPE
			SYNTAX INTEGER
				{
				manual (1),
				auto (2)
				}
			MAX-ACCESS read-write
			STATUS current
			DESCRIPTION
				"Information about DNS source."
			::= { domainNameSystem 4 }
			

		bindNetPort OBJECT-TYPE
			SYNTAX INTEGER
				{
				eth0 (1),
				eth1 (2)
				}
			MAX-ACCESS read-write
			STATUS obsolete
			DESCRIPTION
				"Information about DNS bind net port."
			::= { domainNameSystem 5 }
			

		bindIPProtocol OBJECT-TYPE
			SYNTAX INTEGER
				{
				ipv4 (1),
				ipv6 (2)
				}
			MAX-ACCESS read-write
			STATUS current
			DESCRIPTION
				"Information about DNS bind ip protocol."
			::= { domainNameSystem 6 }
		
                               
--    ****** LDAP Location *******************************  
		ldap  OBJECT IDENTIFIER ::= { hwiBMC 3 }                                

  		ldapEnable OBJECT-TYPE
			SYNTAX INTEGER
			{
				disable (1),
				enable (2)				
			}
			MAX-ACCESS read-write
			STATUS current
			DESCRIPTION
				"The state of LDAP. 
				Default value is disable(1)."
			::= { ldap 1 }
		
		ldapDomainServer OBJECT-TYPE
			SYNTAX DisplayString
			MAX-ACCESS read-write
			STATUS current
			DESCRIPTION
				"LDAP domain server between 1 to 255 characters.
				Default value is 0.0.0.0. Max length is 255 characters."
			::= { ldap 2 } 
			
		ldapUserDomain OBJECT-TYPE
			SYNTAX DisplayString
			MAX-ACCESS read-write
			STATUS current
			DESCRIPTION   
				"LDAP user domain between 1 to 255 characters.
				E.g. CN=employee,OU=company,DC=ldap,DC=ibmc,DC=com or OU=department,OU=company,DC=ldap,DC=ibmc."
			::= { ldap 3 }
			
		ldapPort OBJECT-TYPE
			SYNTAX INTEGER
			MAX-ACCESS read-write
			STATUS current
			DESCRIPTION   
				"Specifies the port number for the LDAP service.
				Value: an integer ranging from 1 to 65535
				The default value is 636."
			::= { ldap 4 }
			
		ldapDomainServer2 OBJECT-TYPE
			SYNTAX DisplayString
			MAX-ACCESS read-write
			STATUS current
			DESCRIPTION
				"LDAP domain server between 1 to 255 characters.
				Default value is 0.0.0.0. Max length is 255 characters."
			::= { ldap 5 } 
			
		ldapUserDomain2 OBJECT-TYPE
			SYNTAX DisplayString
			MAX-ACCESS read-write
			STATUS current
			DESCRIPTION   
				"LDAP user domain between 1 to 255 characters.
				E.g. CN=employee,OU=company,DC=ldap,DC=ibmc,DC=com or OU=department,OU=company,DC=ldap,DC=ibmc."
			::= { ldap 6 }
			
		ldapPort2 OBJECT-TYPE
			SYNTAX INTEGER
			MAX-ACCESS read-write
			STATUS current
			DESCRIPTION   
				"Specifies the port number for the LDAP service.
				Value: an integer ranging from 1 to 65535
				The default value is 636."
			::= { ldap 7 }
		
		ldapDomainServer3 OBJECT-TYPE
			SYNTAX DisplayString
			MAX-ACCESS read-write
			STATUS current
			DESCRIPTION
				"LDAP domain server between 1 to 255 characters.
				Default value is 0.0.0.0. Max length is 255 characters."
			::= { ldap 8 } 
			
		ldapUserDomain3 OBJECT-TYPE
			SYNTAX DisplayString
			MAX-ACCESS read-write
			STATUS current
			DESCRIPTION   
				"LDAP user domain between 1 to 255 characters.
				E.g. CN=employee,OU=company,DC=ldap,DC=ibmc,DC=com or OU=department,OU=company,DC=ldap,DC=ibmc."
			::= { ldap 9 }
			
		ldapPort3 OBJECT-TYPE
			SYNTAX INTEGER
			MAX-ACCESS read-write
			STATUS current
			DESCRIPTION   
				"Specifies the port number for the LDAP service.
				Value: an integer ranging from 1 to 65535
				The default value is 636."
			::= { ldap 10 }

		ldapGroupInfoDescription1Table OBJECT-TYPE
			SYNTAX SEQUENCE OF LDAPGroupInfoDescription1Entry 
			MAX-ACCESS not-accessible
			STATUS current
			DESCRIPTION
				"A table containing the list of LDAP information."
			::= { ldap 50 }
        
        ldapGroupInfoDescription1Entry OBJECT-TYPE
			SYNTAX LDAPGroupInfoDescription1Entry  
			MAX-ACCESS not-accessible
			STATUS current
			DESCRIPTION
				"."
			INDEX { groupIndex }
			::= { ldapGroupInfoDescription1Table 1 }
		
		LDAPGroupInfoDescription1Entry ::=
			SEQUENCE {
				groupIndex
					INTEGER, 
				groupName
					DisplayString, 
				groupDomain
					DisplayString,
				groupPrivilege 
					INTEGER,
				groupInterfaces
				    INTEGER
				}  
				

		groupIndex OBJECT-TYPE	
			SYNTAX INTEGER
			MAX-ACCESS not-accessible
			STATUS current
			DESCRIPTION
				"LDAP group index."
			::= { ldapGroupInfoDescription1Entry 1 } 
				

		groupName OBJECT-TYPE	
			SYNTAX DisplayString
			MAX-ACCESS read-write
			STATUS current
			DESCRIPTION
				"LDAP group name between 0 to 32 characters."
			::= { ldapGroupInfoDescription1Entry 2 } 
			

		groupDomain OBJECT-TYPE
			SYNTAX DisplayString
			MAX-ACCESS read-write
			STATUS current
			DESCRIPTION
				"LDAP group domain between 0 to 255 characters.
				E.g. Group0 CN=group0,DC=ldap,DC=ibmc,DC=com."
			::= { ldapGroupInfoDescription1Entry 3 }   
			

		groupPrivilege OBJECT-TYPE
			SYNTAX INTEGER
			{
				commonUser(1),
				operator(2),	
				administrator(3),
				customRole1(4),
				customRole2(5),
				customRole3(6),
				customRole4(7)
			}	
			MAX-ACCESS read-write
			STATUS current
			DESCRIPTION
				"1 - common user
				 2 - operator 
				 3 - administrator
				 4 - custom role1
				 5 - custom role2
				 6 - custom role3
				 7 - custom role4
				 Default value is commonUser(1)."
			::= { ldapGroupInfoDescription1Entry 4 } 
			
		groupInterfaces OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription1Entry 5 }

		ldapGroupInfoDescription2Table OBJECT-TYPE
			SYNTAX SEQUENCE OF LDAPGroupInfoDescription2Entry 
			MAX-ACCESS not-accessible
			STATUS current
			DESCRIPTION
				"A table containing the list of LDAP information."
			::= { ldap 51 }
        
        ldapGroupInfoDescription2Entry OBJECT-TYPE
			SYNTAX LDAPGroupInfoDescription2Entry  
			MAX-ACCESS not-accessible
			STATUS current
			DESCRIPTION
				"."
			INDEX { groupIndex2 }
			::= { ldapGroupInfoDescription2Table 1 }
		
		LDAPGroupInfoDescription2Entry ::=
			SEQUENCE {
				groupIndex2
					INTEGER, 
				groupName2
					DisplayString,		
				groupPrivilege2 
					INTEGER,
				groupInterfaces2
				    INTEGER,
				groupDomain2
					DisplayString
				}  
				

		groupIndex2 OBJECT-TYPE	
			SYNTAX INTEGER
			MAX-ACCESS not-accessible
			STATUS current
			DESCRIPTION
				"LDAP group index."
			::= { ldapGroupInfoDescription2Entry 1 } 
				

		groupName2 OBJECT-TYPE	
			SYNTAX DisplayString
			MAX-ACCESS read-write
			STATUS current
			DESCRIPTION
				"LDAP group name between 0 to 32 characters."
			::= { ldapGroupInfoDescription2Entry 2 } 

		groupPrivilege2 OBJECT-TYPE
			SYNTAX INTEGER
			{
				commonUser(1),
				operator(2),	
				administrator(3),
				customRole1(4),
				customRole2(5),
				customRole3(6),
				customRole4(7)
			}	
			MAX-ACCESS read-write
			STATUS current
			DESCRIPTION
				"1 - common user
				 2 - operator 
				 3 - administrator
				 4 - custom role1
				 5 - custom role2
				 6 - custom role3
				 7 - custom role4
				 Default value is commonUser(1)."
			::= { ldapGroupInfoDescription2Entry 3 }  
			
		groupInterfaces2 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription2Entry 4 }
			
		groupDomain2 OBJECT-TYPE
			SYNTAX DisplayString
			MAX-ACCESS read-write
			STATUS current
			DESCRIPTION
				"LDAP group domain between 0 to 255 characters.
				E.g. Group0 CN=group0,DC=ldap,DC=ibmc,DC=com."
			::= { ldapGroupInfoDescription2Entry 5 }  
			
		ldapGroupInfoDescription3Table OBJECT-TYPE
			SYNTAX SEQUENCE OF LDAPGroupInfoDescription3Entry 
			MAX-ACCESS not-accessible
			STATUS current
			DESCRIPTION
				"A table containing the list of LDAP information."
			::= { ldap 52 }
        
        ldapGroupInfoDescription3Entry OBJECT-TYPE
			SYNTAX LDAPGroupInfoDescription3Entry  
			MAX-ACCESS not-accessible
			STATUS current
			DESCRIPTION
				"."
			INDEX { groupIndex3 }
			::= { ldapGroupInfoDescription3Table 1 }
		
		LDAPGroupInfoDescription3Entry ::=
			SEQUENCE {
				groupIndex3
					INTEGER, 
				groupName3
					DisplayString, 
				groupPrivilege3 
					INTEGER,
				groupInterfaces3
				    INTEGER,
				groupDomain3
					DisplayString
				}  
				

		groupIndex3 OBJECT-TYPE	
			SYNTAX INTEGER
			MAX-ACCESS not-accessible
			STATUS current
			DESCRIPTION
				"LDAP group index."
			::= { ldapGroupInfoDescription3Entry 1 } 
				

		groupName3 OBJECT-TYPE	
			SYNTAX DisplayString
			MAX-ACCESS read-write
			STATUS current
			DESCRIPTION
				"LDAP group name between 0 to 32 characters."
			::= { ldapGroupInfoDescription3Entry 2 } 

		groupPrivilege3 OBJECT-TYPE
			SYNTAX INTEGER
			{
				commonUser(1),
				operator(2),	
				administrator(3),
				customRole1(4),
				customRole2(5),
				customRole3(6),
				customRole4(7)
			}	
			MAX-ACCESS read-write
			STATUS current
			DESCRIPTION
				"1 - common user
				 2 - operator 
				 3 - administrator
				 4 - custom role1
				 5 - custom role2
				 6 - custom role3
				 7 - custom role4
				 Default value is commonUser(1)."
			::= { ldapGroupInfoDescription3Entry 3 }  	
			
		groupInterfaces3 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription3Entry 4 }
			
		groupDomain3 OBJECT-TYPE
			SYNTAX DisplayString
			MAX-ACCESS read-write
			STATUS current
			DESCRIPTION
				"LDAP group domain between 0 to 255 characters.
				E.g. Group0 CN=group0,DC=ldap,DC=ibmc,DC=com."
			::= { ldapGroupInfoDescription3Entry 5 } 
			
--    ****** Trap Location *******************************  			

		trap  OBJECT IDENTIFIER ::= { hwiBMC 4 }                                
        

  		trapEnable OBJECT-TYPE
			SYNTAX INTEGER
					{
					disable (1),
					enable (2)				
					}
			MAX-ACCESS read-write
			STATUS current
			DESCRIPTION
				"The state of Trap. 
				Default value is enable(2)."
			::= { trap 1 }
		 

		 trapCommunity OBJECT-TYPE
			SYNTAX DisplayString
			MAX-ACCESS read-write
			STATUS current
			DESCRIPTION
				"SNMP trap community between 1 to 18 characters.
				A community supports all characters except space."
			::= { trap 2 } 
		

		 trapLevel OBJECT-TYPE
			SYNTAX INTEGER
				{
				 ok(1),
				 minor(2),
				 major(3),
				 critical(4) 
				}
			MAX-ACCESS read-write
			STATUS current
			DESCRIPTION
				"The level of trap send.
				Default level is minor.
				ok:send all level message.
				minor:send minor and above level message.
				major:send major and above level message.
				critical:send critical level message."
			::= { trap 3 }                        

		trapMode OBJECT-TYPE
			SYNTAX INTEGER
			{
			eventCodeMode(1),
			trapOidMode(2)
			}
			
			MAX-ACCESS read-write
			STATUS current
			DESCRIPTION
				"Trap mode."
			::= { trap 4 }  
			
		trapVersion OBJECT-TYPE
			SYNTAX INTEGER
			{
			v1(1),
			v2c(2),
			v3(3)
			}
			
			MAX-ACCESS read-write
			STATUS current
			DESCRIPTION
				"Trap version."
			::= { trap 5 } 
			
		trapRearm OBJECT-TYPE
			SYNTAX INTEGER
			{
			rearm(1)
			}
			
			MAX-ACCESS read-write
			STATUS current
			DESCRIPTION
				"Send rearm commomnd."
			::= { trap 6 } 
			
		trapServerIdentity OBJECT-TYPE
			SYNTAX INTEGER
			{
			 boardSN(1),
			 productAssetTag(2),
			 hostName(3)
			}
			
			MAX-ACCESS read-write
			STATUS current
			DESCRIPTION
				"Choose the server Identity when sending trap."
			::= { trap 7 }
			
		trapSecurityUserName OBJECT-TYPE
			SYNTAX DisplayString
			MAX-ACCESS read-write
			STATUS current
			DESCRIPTION
				"The security user name for SNMP TRAP V3, the user should be one of the BMC local user."
			::= { trap 8 }  

		 trapLevelDetail OBJECT-TYPE
			SYNTAX DisplayString
			MAX-ACCESS read-write
			STATUS current
			DESCRIPTION
				"The level of trap send.
				Support set/get any combination of the 4 alarm levels(critical,major,minor,normal), use comma to separate them.
				none/all is also supported,but never use it with the 4 levels together.
				
				e.g. To set critical + major level message, just set:
						critical,major
					To set critical level message, just set:
						critical
					To set all level message, just set:
						all"						
			::= { trap 9 } 
			
		--Trap
		trapInfoDescriptionTable OBJECT-TYPE
			SYNTAX SEQUENCE OF TrapInfoDescriptionEntry
			MAX-ACCESS not-accessible
			STATUS current
			DESCRIPTION
				"A table containing the list of Trap information."
			::= { trap 50 }
        
                trapInfoDescriptionEntry OBJECT-TYPE
			SYNTAX TrapInfoDescriptionEntry  
			MAX-ACCESS not-accessible
			STATUS current
			DESCRIPTION
				"Information about a trap group."
			INDEX { trapReceiverIndex }
			::= { trapInfoDescriptionTable 1 }
		
		TrapInfoDescriptionEntry ::=
			SEQUENCE {
				trapReceiverIndex
					INTEGER,
				trapReceiverEnable
					INTEGER,
				trapReceiverAddress
					DisplayString,
				trapReceiverPort 
					INTEGER,    
				trapSendType
					INTEGER,
				trapTest
					INTEGER																 					
				} 
			
		trapReceiverIndex OBJECT-TYPE	
			SYNTAX INTEGER
			MAX-ACCESS not-accessible
			STATUS current
			DESCRIPTION
				""
			::= { trapInfoDescriptionEntry 1 } 
		

		trapReceiverEnable OBJECT-TYPE
			SYNTAX INTEGER      
			{
				disable(1),
				enable(2)	
			}
			MAX-ACCESS read-write
			STATUS current
			DESCRIPTION
				"Trap Receiver state enable 2,
				 disable 1."
			::= { trapInfoDescriptionEntry 2 }
        

		trapReceiverAddress OBJECT-TYPE
			SYNTAX DisplayString
			MAX-ACCESS read-write
			STATUS current
			DESCRIPTION
				"Trap Receiver IPv4 addrsss.
				Default value is empty."
			::= { trapInfoDescriptionEntry 3 }  


		trapReceiverPort OBJECT-TYPE
			SYNTAX INTEGER
			MAX-ACCESS read-write
			STATUS current
			DESCRIPTION
				"SNMP trap port, default is 162."
			::= { trapInfoDescriptionEntry 4 } 
	

		trapSendType OBJECT-TYPE
			SYNTAX INTEGER 
			{
				snmpTrap(1)	
			}
			MAX-ACCESS read-write
			STATUS current
			DESCRIPTION
				"Send message type snmptrap."
			::= { trapInfoDescriptionEntry 5 }
		

		trapTest OBJECT-TYPE
			SYNTAX INTEGER 
			MAX-ACCESS read-write
			STATUS current
			DESCRIPTION
				"Test the SNMP trap or syslog whether could send.
				When set, the value is only 1."
			::= { trapInfoDescriptionEntry 6 }   
			
--    ****** SMTP Location *******************************  			

		smtp  OBJECT IDENTIFIER ::= { hwiBMC 5 }                                

  		smtpEnable OBJECT-TYPE
			SYNTAX INTEGER
			{
				disable (1),
				enable (2)				
			}
			MAX-ACCESS read-write
			STATUS current
			DESCRIPTION
				"The state of SMTP. 
				Default value is disable(1)."
			::= { smtp 1 }
		 

		smtpSendSeverity OBJECT-TYPE
			SYNTAX INTEGER
				{
				 ok(1),
				 minor(2),
				 major(3),
				 critical(4) 
				}
			MAX-ACCESS read-write
			STATUS current
			DESCRIPTION
				"The severity of SMTP send.
				Default Severity is ok(1).
				ok:Send all level message.
				minor:Send minor and above level message.
				major:Send major and above level message.
				critical:Send critical level message."
			::= { smtp 2 }
		

		smtpServerIP OBJECT-TYPE
			SYNTAX DisplayString
			MAX-ACCESS read-write
			STATUS current
			DESCRIPTION
				"The SMTP server IP address.
				Default value is empty."
			::= { smtp 3 } 
			

		smtpLoginType OBJECT-TYPE
			SYNTAX INTEGER
			{
				anonymous(1),
				account(2)
			}
			MAX-ACCESS read-write
			STATUS current
			DESCRIPTION
				"SMTP login type anonymous 1, account 2.
				Default value is anonymous(1)."
			::= { smtp 4 } 	
			

		smtpLoginAccount OBJECT-TYPE
			SYNTAX DisplayString
			MAX-ACCESS read-write
			STATUS current
			DESCRIPTION
				"Login account between 1 to 64 characters.
				A login account supports all characters except space,double quotationthe,equal and the following characters:#'&."
			::= { smtp 5 } 
			

		smtpLoginPassword OBJECT-TYPE
			SYNTAX DisplayString
			MAX-ACCESS read-write
			STATUS current
			DESCRIPTION
				"Set user login SMTP password.
				Login password between 1 to 50 characters."
			::= { smtp 6 }
			

		smtpSendFrom OBJECT-TYPE
			SYNTAX DisplayString
			MAX-ACCESS read-write
			STATUS current
			DESCRIPTION
				"Send from between 0 to 255 characters.
				A send from supports all characters except space,double quotation,equal and the following characters:#'&."
			::= { smtp 7 }			
			
		smtpTLSEnable OBJECT-TYPE
			SYNTAX INTEGER
			{
				disable (1),
				enable (2)				
			}
			MAX-ACCESS read-write
			STATUS current
			DESCRIPTION
				"The TLS state for SMTP. 
				Default value is enable(2)."
			::= { smtp 8 }			
			

		smtpSendSeverityDetail OBJECT-TYPE
			SYNTAX DisplayString
			MAX-ACCESS read-write
			STATUS current
			DESCRIPTION
				"The severity of SMTP send.
				Support set/get any combination of the 4 alarm levels(critical,major,minor,normal), use comma to separate them.
				none/all is also supported,but never use it with the 4 levels together.
				
				e.g. To set critical + major level message, just set:
						critical,major
					To set critical level message, just set:
						critical
					To set all level message, just set:
						all"	
			::= { smtp 9 }			
			

 		smtpReceiverDescriptionTable OBJECT-TYPE
			SYNTAX SEQUENCE OF SmtpReceiverDescriptionEntry 
			MAX-ACCESS not-accessible
			STATUS current
			DESCRIPTION
				"A table containing the list of SMTP Receiver information."
			::= { smtp 50 }
        
                smtpReceiverDescriptionEntry OBJECT-TYPE
			SYNTAX SmtpReceiverDescriptionEntry  
			MAX-ACCESS not-accessible
			STATUS current
			DESCRIPTION
				"Information about SMTP Receiver information."
			INDEX { smtpReceiverIndex }
			::= { smtpReceiverDescriptionTable 1 }
		
		SmtpReceiverDescriptionEntry ::=
			SEQUENCE {
				smtpReceiverIndex
					INTEGER,
				smtpReceiverState
					INTEGER,
				smtpReceiverAddress
					DisplayString,
				smtpReceiverDescription 
					DisplayString,    
				smtpReceiverTest
					INTEGER																 					
				} 

		smtpReceiverIndex OBJECT-TYPE	
			SYNTAX INTEGER
			MAX-ACCESS not-accessible
			STATUS current
			DESCRIPTION
				"Smtp receiver index."
			::= { smtpReceiverDescriptionEntry 1 } 


		smtpReceiverState OBJECT-TYPE
			SYNTAX INTEGER      
				{
				disable(1),
				enable(2)	
				}
			MAX-ACCESS read-write
			STATUS current
			DESCRIPTION
				"SMTP receiver enable state. Disable 1, enable 2.
				Default value is disable(1)."
			::= { smtpReceiverDescriptionEntry 2 }
        

		smtpReceiverAddress OBJECT-TYPE
			SYNTAX DisplayString
			MAX-ACCESS read-write
			STATUS current
			DESCRIPTION
				"Email address between 0 to 255 characters.
				A email address supports all characters except space,double quotation,equal and the following characters:#'&."
			::= { smtpReceiverDescriptionEntry 3 }  
		

		smtpReceiverDescription OBJECT-TYPE
			SYNTAX DisplayString
			MAX-ACCESS read-write
			STATUS current
			DESCRIPTION
				"Email description between 0 to 255 characters.
				A email description supports all characters except double quotation,equal and the following characters:#'&."
			::= { smtpReceiverDescriptionEntry 4 } 
		

		smtpReceiverTest OBJECT-TYPE
			SYNTAX INTEGER 
			MAX-ACCESS read-write
			STATUS current
			DESCRIPTION
				"Test whether could send email.
				When set, the value is only 1."
			::= { smtpReceiverDescriptionEntry 5 }

--    ****** Syslog Location *******************************

		syslog  OBJECT IDENTIFIER ::= { hwiBMC 34 }


  		syslogEnable OBJECT-TYPE
			SYNTAX INTEGER
					{
					disable (1),
					enable (2)
					}
			MAX-ACCESS read-write
			STATUS current
			DESCRIPTION
				"The enable state of syslog.
				Default value is disable(1)."
			::= { syslog 1 }

		syslogIdentity OBJECT-TYPE
			SYNTAX INTEGER
			{
			 boardSN(1),
			 productAssetTag(2),
			 hostName(3)
			}

			MAX-ACCESS read-write
			STATUS current
			DESCRIPTION
				"Choose the server Identity when sending syslog."
			::= { syslog 2 }

		 syslogSeverity OBJECT-TYPE
			SYNTAX INTEGER
				{
				 ok(1),
				 minor(2),
				 major(3),
				 critical(4),
				 none(5)
				}
			MAX-ACCESS read-write
			STATUS current
			DESCRIPTION
				"The level of syslog send.
				Default level is ok.
				ok:send all level message.
				minor:send minor and above level message.
				major:send major and above level message.
				critical:send critical level message.
				none:send nothing."
			::= { syslog 3 }
		
		syslogProtocolType OBJECT-TYPE
			SYNTAX INTEGER
				{
				udp(1),
				tcp(2),
				tls(3)
				}
			MAX-ACCESS read-write
			STATUS current
			DESCRIPTION
				"The syslog protocol type.
				Default value is TCP.
				udp:When receiving messages using the UDP protocol.
				tcp:When receiving messages using the TCP protocol.
				tls:When receiving messages using the TCP protocol"
			::= { syslog 4 }
		
		syslogAuthType OBJECT-TYPE
			SYNTAX INTEGER
				{
				one-way(1),
				mutual(2)
				}
			MAX-ACCESS read-write
			STATUS current
			DESCRIPTION
				"The syslog auth type.
				Default value is one way authentication.
				one way authentication:authenticate the server.
				mutual authentication:authenticate the server and client."
			::= { syslog 5 }
			
		syslogImportRootCertificate OBJECT-TYPE
			SYNTAX DisplayString
			MAX-ACCESS read-write
			STATUS current
			DESCRIPTION
				"Import root certificate of the syslog server,write only. eg:/tmp/cacert.pem"
			::= { syslog 6 }
		
		syslogImportClientCertificate OBJECT-TYPE
			SYNTAX DisplayString
			MAX-ACCESS read-write
			STATUS current
			DESCRIPTION
				"Import client certificate of the syslog server,write only. eg:/tmp/client.pfx;password"
			::= { syslog 7 }

		--Syslog
		syslogInfoDescriptionTable OBJECT-TYPE
			SYNTAX SEQUENCE OF SyslogInfoDescriptionEntry
			MAX-ACCESS not-accessible
			STATUS current
			DESCRIPTION
				"A table containing the list of Syslog information."
			::= { syslog 50 }

		syslogInfoDescriptionEntry OBJECT-TYPE
			SYNTAX SyslogInfoDescriptionEntry
			MAX-ACCESS not-accessible
			STATUS current
			DESCRIPTION
				"Information about a syslog group."
			INDEX { syslogReceiverIndex }
			::= { syslogInfoDescriptionTable 1 }

		SyslogInfoDescriptionEntry ::=
			SEQUENCE {
				syslogReceiverIndex
					INTEGER,
				syslogReceiverEnable
					INTEGER,
				syslogReceiverAddress
					DisplayString,
				syslogReceiverPort
					INTEGER,
				syslogSendLogType
					DisplayString,
				syslogReceiverTest
					INTEGER
				}

		syslogReceiverIndex OBJECT-TYPE
			SYNTAX INTEGER
			MAX-ACCESS not-accessible
			STATUS current
			DESCRIPTION
				""
			::= { syslogInfoDescriptionEntry 1 }


		syslogReceiverEnable OBJECT-TYPE
			SYNTAX INTEGER
			{
				disable(1),
				enable(2)
			}
			MAX-ACCESS read-write
			STATUS current
			DESCRIPTION
				"Syslog Receiver state enable 2,
				 disable 1."
			::= { syslogInfoDescriptionEntry 2 }


		syslogReceiverAddress OBJECT-TYPE
			SYNTAX DisplayString
			MAX-ACCESS read-write
			STATUS current
			DESCRIPTION
				"Syslog Receiver IP addrsss.
				Default value is empty."
			::= { syslogInfoDescriptionEntry 3 }


		syslogReceiverPort OBJECT-TYPE
			SYNTAX INTEGER
			MAX-ACCESS read-write
			STATUS current
			DESCRIPTION
				"Syslog port."
			::= { syslogInfoDescriptionEntry 4 }

		syslogSendLogType OBJECT-TYPE
			SYNTAX DisplayString
			MAX-ACCESS read-write
			STATUS current
			DESCRIPTION
				"The log type of syslog send.
				Support set/get any combination of the 3 log type(OperationLogs,SecurityLogs,EventLogs), use comma to separate them.
				none/all is also supported,but never use it with the 3 log types together.

				e.g. To set OperationLogs + SecurityLogs log type message, just set:
						OperationLogs,SecurityLogs
					To set EventLogs message, just set:
						EventLogs
					To set none level message, just set:
						none
					To set all level message, just set:
						all"
			::= { syslogInfoDescriptionEntry 5 }

		syslogReceiverTest OBJECT-TYPE
			SYNTAX INTEGER
			MAX-ACCESS read-write
			STATUS current
			DESCRIPTION
				"Test the syslog.
				When set, the value is only 1."
			::= { syslogInfoDescriptionEntry 6 }
		
		--syslog cert 
		syslogCertInfoDescriptionTable OBJECT-TYPE
			SYNTAX SEQUENCE OF SyslogCertInfoDescriptionEntry
			MAX-ACCESS not-accessible
			STATUS current
			DESCRIPTION
				"A table containing the list of Syslog cert information.
				1:root CA.
				2:client cert."
			::= { syslog 51 }
		syslogCertInfoDescriptionEntry OBJECT-TYPE
			SYNTAX SyslogCertInfoDescriptionEntry
			MAX-ACCESS not-accessible
			STATUS current
			DESCRIPTION
				"Information about a syslog cert group."
			INDEX { syslogCertType }
			::= { syslogCertInfoDescriptionTable 1 }

		SyslogCertInfoDescriptionEntry ::=
			SEQUENCE {
				syslogCertType
					INTEGER,
				syslogCertIssuedTo
					DisplayString,
				syslogCertIssuedBy
					DisplayString,
				syslogCertValidFrom
					DisplayString,
				syslogCertValidTo
					DisplayString,
				syslogCertSerialNumber
					DisplayString
				}
				
		syslogCertType OBJECT-TYPE
			SYNTAX INTEGER
			MAX-ACCESS not-accessible
			STATUS current
			DESCRIPTION
				"1: The root CA of syslog server. 
				 2: The client certificate of iBMC."
			::= { syslogCertInfoDescriptionEntry 1 }
		syslogCertIssuedTo OBJECT-TYPE
			SYNTAX DisplayString
			MAX-ACCESS read-only
			STATUS current
			DESCRIPTION
				"Provides information about the user (current server) of an SSL certificate."
			::= { syslogCertInfoDescriptionEntry 2 }
		syslogCertIssuedBy OBJECT-TYPE
			SYNTAX DisplayString
			MAX-ACCESS read-only
			STATUS current
			DESCRIPTION
				"Provides information about the issuer of an SSL certificate. The fields 
				contained in Issued By are the same as those in Issued To."
			::= { syslogCertInfoDescriptionEntry 3 }
		syslogCertValidFrom OBJECT-TYPE
			SYNTAX DisplayString
			MAX-ACCESS read-only
			STATUS current
			DESCRIPTION
				"Indicates the date when an SSL certificate starts to take effect."
			::= { syslogCertInfoDescriptionEntry 4 }
		syslogCertValidTo OBJECT-TYPE
			SYNTAX DisplayString
			MAX-ACCESS read-only
			STATUS current
			DESCRIPTION
				"Indicates the date when an SSL certificate will expire."
			::= { syslogCertInfoDescriptionEntry 5 }
		syslogCertSerialNumber OBJECT-TYPE
			SYNTAX DisplayString
			MAX-ACCESS read-only
			STATUS current
			DESCRIPTION
				"Indicates the serial number of an SSL certificate, used for identifying and 
				migrating the certificate."
			::= { syslogCertInfoDescriptionEntry 6 }
--    ****** PowerSupply Location *******************************
  
		powerSupplyInfo OBJECT IDENTIFIER ::= { hwiBMC 6 }
		

		powerSupplyEntireStatus OBJECT-TYPE
			SYNTAX INTEGER 
				{
				ok(1),
				minor(2),
				major(3),
				critical(4),
				absence(5),
				unknown(6)
				}
			MAX-ACCESS read-only
			STATUS current
			DESCRIPTION
				"Information about all power supply health status."
			::= { powerSupplyInfo 1 }
			
		settedPowerSupplyEntireMode OBJECT-TYPE
			SYNTAX INTEGER 
				{
				loadBalance(1),
				activeStandby(2),
				unsupport(3) 
				}
			MAX-ACCESS read-write
			STATUS current
			DESCRIPTION
				"Setted power supply entire mode.
				 Power supply entire mode get:
					1:loadBalance(1)
					2:activeBackup(2)
					3:unsupport(3) 
				 Power supply entire mode set:
					1:loadBalance(1)
					2:activeBackup(2)
				"
			::= { powerSupplyInfo 2 }
                       
		actualPowerSupplyEntireMode OBJECT-TYPE
			SYNTAX INTEGER 
				{
				loadBalance(1),
				activeStandby(2),
				unknown(3)
				}
			MAX-ACCESS read-only
			STATUS current
			DESCRIPTION
				"Actual power supply entire mode."
			::= { powerSupplyInfo 3 }
			
		settedActivePowerSupply OBJECT-TYPE
			SYNTAX INTEGER 
			MAX-ACCESS read-write
			STATUS current
			DESCRIPTION
				"Setted active power supply. per bit represents a PS, bit0 is PS1, and so on, the bit value of 1 indicates the PS is active.can not set all PS are active or backup.The result 0x7FFFFFFF is unsupport."
			::= { powerSupplyInfo 4 }	
			
		powerSupplyDescriptionTable OBJECT-TYPE
			SYNTAX SEQUENCE OF PowerSupplyDescriptionEntry 
			MAX-ACCESS not-accessible
			STATUS current
			DESCRIPTION
				"A table containing the list of power supply information."
			::= { powerSupplyInfo 50 }
        
                powerSupplyDescriptionEntry OBJECT-TYPE
			SYNTAX PowerSupplyDescriptionEntry
			MAX-ACCESS not-accessible
			STATUS current
			DESCRIPTION
				"Information about power supply."
			INDEX { powerSupplyIndex }
			::= { powerSupplyDescriptionTable 1 }
		
		PowerSupplyDescriptionEntry ::=
			SEQUENCE {
				powerSupplyIndex
					INTEGER, 
				powerSupplymanufacture 
					DisplayString,
				powerSupplyInputMode
					INTEGER,
				powerSupplyModel 
					DisplayString,
				powerSupplyVersion 
					DisplayString, 
				powerSupplyPowerRating 
					INTEGER, 
				powerSupplyStatus 
					INTEGER, 					
				powerSupplyInputPower 
					INTEGER,
				powerSupplyPresence 
					INTEGER,
				powerSupplyProtocol
				    INTEGER	,
				powerSupplyLocation 
					DisplayString,
				powerSupplyFunction
					DisplayString,
				powerSupplyDevicename
				    DisplayString,
				powerSupplyWorkMode
					INTEGER    						
				} 

		powerSupplyIndex OBJECT-TYPE	
			SYNTAX INTEGER
			MAX-ACCESS not-accessible
			STATUS current
			DESCRIPTION
				"Power supply index."
			::= { powerSupplyDescriptionEntry 1 } 
			

		powerSupplymanufacture OBJECT-TYPE
			SYNTAX DisplayString
			MAX-ACCESS read-only
			STATUS current
			DESCRIPTION
				"Information about power manufacture."
			::= { powerSupplyDescriptionEntry 2 }
			

		powerSupplyInputMode OBJECT-TYPE
			SYNTAX INTEGER
			{
			acInput(1),
			dcInput(2),
			acInputDcInput(3)
			}
			MAX-ACCESS read-only
			STATUS current
			DESCRIPTION
				"Information about power input."
			::= { powerSupplyDescriptionEntry 3 }
			

		powerSupplyModel OBJECT-TYPE
			SYNTAX DisplayString
			MAX-ACCESS read-only
			STATUS current
			DESCRIPTION
				"Information about power Model."
			::= { powerSupplyDescriptionEntry 4 } 
			
			

		powerSupplyVersion OBJECT-TYPE
			SYNTAX DisplayString
			MAX-ACCESS read-only
			STATUS current
			DESCRIPTION
				"Information about power version."
			::= { powerSupplyDescriptionEntry 5 }  

			

		powerSupplyPowerRating OBJECT-TYPE
			SYNTAX INTEGER
			MAX-ACCESS read-only
			STATUS current
			DESCRIPTION
				"Information about power rating."
			::= { powerSupplyDescriptionEntry 6 } 			



		powerSupplyStatus OBJECT-TYPE
			SYNTAX INTEGER  
				{
				ok(1),
				minor(2),
				major(3),
				critical(4),
				absence(5),
				unknown(6)
				}
			MAX-ACCESS read-only
			STATUS current
			DESCRIPTION
				"Information about power status."
			::= { powerSupplyDescriptionEntry 7 } 			


		powerSupplyInputPower OBJECT-TYPE
			SYNTAX INTEGER
			MAX-ACCESS read-only
			STATUS current
			DESCRIPTION
				"Information about input power.
				The unit is watt."
			::= { powerSupplyDescriptionEntry 8 } 			    
			

		powerSupplyPresence OBJECT-TYPE
			SYNTAX INTEGER 
				{
				absence(1),
				presence(2),
				unknown(3)
				}
			MAX-ACCESS read-only
			STATUS current
			DESCRIPTION
				"Information about power presence status."
			::= { powerSupplyDescriptionEntry 9 } 
			

		powerSupplyProtocol OBJECT-TYPE
			SYNTAX INTEGER 
				{
				psmi(1),
				pmbus(2)
				}
			MAX-ACCESS read-only
			STATUS current
			DESCRIPTION
				"Information about power protocol."
			::= { powerSupplyDescriptionEntry 10 }
			
		powerSupplyLocation OBJECT-TYPE
			SYNTAX DisplayString
			MAX-ACCESS read-only
			STATUS current
			DESCRIPTION
				"Power supply physical location."
			::= { powerSupplyDescriptionEntry 11 }
		powerSupplyFunction OBJECT-TYPE
			SYNTAX DisplayString
			MAX-ACCESS read-only
			STATUS current
			DESCRIPTION
				"Power supply logic function."
			::= { powerSupplyDescriptionEntry 12 }
		powerSupplyDevicename OBJECT-TYPE
			SYNTAX DisplayString
			MAX-ACCESS read-only
			STATUS current
			DESCRIPTION
				"Power supply devicename."
			::= { powerSupplyDescriptionEntry 13 }	
			
		powerSupplyWorkMode OBJECT-TYPE
			SYNTAX INTEGER 
				{
				active(1),
				backup(2),
				unknown(3)
				}
			MAX-ACCESS read-only
			STATUS current
			DESCRIPTION
				"power supply actual work mode."
			::= { powerSupplyDescriptionEntry 14 }	
			
--    ****** FRU Power Control Property *******************************
  
		fruPowerProperty OBJECT IDENTIFIER ::= { hwiBMC 7 }    

		fruPowerDescriptionTable OBJECT-TYPE
			SYNTAX SEQUENCE OF FruPowerDescriptionEntry 
			MAX-ACCESS not-accessible
			STATUS current
			DESCRIPTION
				"A table containing the list of fru power information."
			::= { fruPowerProperty 50 }
        
                fruPowerDescriptionEntry OBJECT-TYPE
			SYNTAX FruPowerDescriptionEntry
			MAX-ACCESS not-accessible
			STATUS current
			DESCRIPTION
				"Information about fru power supply."
			INDEX { fruNum }
			::= { fruPowerDescriptionTable 1 }
		
		FruPowerDescriptionEntry ::=
			SEQUENCE {
				fruNum
					INTEGER,
				fruPowerControl
					INTEGER
				}
				 

		fruNum OBJECT-TYPE	
			SYNTAX INTEGER
			MAX-ACCESS not-accessible
			STATUS current
			DESCRIPTION
				"The index of the FRU power."
			::= { fruPowerDescriptionEntry 1 }
					
			

		fruPowerControl OBJECT-TYPE
			SYNTAX INTEGER
				{
				normalPowerOff(1),
				powerOn(2),
				forcedSystemReset(3),
				forcedPowerCycle(4)
				}
			MAX-ACCESS read-write
			STATUS current
			DESCRIPTION
				"Information about fru power control."
			::= { fruPowerDescriptionEntry 2 }
			                                                     
--    ****** FAN Information *******************************
  
		fanProperty OBJECT IDENTIFIER ::= { hwiBMC 8 }     
		 

		fanMode OBJECT-TYPE
			SYNTAX DisplayString
			MAX-ACCESS read-write
			STATUS current
			DESCRIPTION
				"Fan control mode manual or auto. 
				 fan mode:   
				 0  - auto	
				 1  - manual	           
				 
				 set format: <mode>,[timeout]
				 get format: <mode>,[timeout]   
				 
				 When <mode> = 0, the format is only <mode>.
				    
				 [timeout] is option and value is in [0,300],unit is second,
				 When set, if fan mode is manual and without [timeout],
				 The default out time is 30 seconds."
			::= { fanProperty 1 } 
			     

		fanLevel OBJECT-TYPE
			SYNTAX INTEGER
			MAX-ACCESS read-write
			STATUS current
			DESCRIPTION
				"Percent of fan speed.
				This value is in [MIN_FANLEVEL,100].
				MIN_FANLEVEL is the minimum fanlevel according to systems,
				particular, when get, 255 represent fan mode is auto."
			::= { fanProperty 2 }
			

		fanEntireStatus OBJECT-TYPE
			SYNTAX INTEGER 
				{
				ok(1),
				minor(2),
				major(3),
				critical(4),
				absence(5),
				unknown(6)
				}
			MAX-ACCESS read-only
			STATUS current
			DESCRIPTION
				"Information about all fan health status."
			::= { fanProperty 3 }
        
		fanDescriptionTable OBJECT-TYPE
			SYNTAX SEQUENCE OF FanDescriptionEntry 
			MAX-ACCESS not-accessible
			STATUS current
			DESCRIPTION
				"A table containing the list of fan information."
			::= { fanProperty 50 }
        
                fanDescriptionEntry OBJECT-TYPE
			SYNTAX FanDescriptionEntry
			MAX-ACCESS not-accessible
			STATUS current
			DESCRIPTION
				"Information about fan information."
			INDEX { fanIndex }
			::= { fanDescriptionTable 1 }
		
		FanDescriptionEntry ::=
			SEQUENCE {
				fanIndex
					INTEGER, 
				fanSpeed
					INTEGER,
				fanPresence
					INTEGER,
				fanStatus
					INTEGER,
				fanLocation
					DisplayString,
				fanFunction
					DisplayString,
				fanDevicename
					DisplayString	
				}
				 

		fanIndex OBJECT-TYPE	
			SYNTAX INTEGER
			MAX-ACCESS not-accessible
			STATUS current
			DESCRIPTION
				"Fan index."
			::= { fanDescriptionEntry 1 } 
			
			

		fanSpeed OBJECT-TYPE
			SYNTAX INTEGER
			MAX-ACCESS read-only
			STATUS current
			DESCRIPTION
				"Information about fan speed, Unit is RPM."
			::= { fanDescriptionEntry 2 } 
			

		fanPresence OBJECT-TYPE
			SYNTAX INTEGER
				{
				absence(1),
				presence(2),
				unknown(3)
				}
			MAX-ACCESS read-only
			STATUS current
			DESCRIPTION
				"Information about fan presence."
			::= { fanDescriptionEntry 3 }



		fanStatus OBJECT-TYPE
			SYNTAX INTEGER 
				{
				ok(1),
				minor(2),
				major(3),
				critical(4),
				absence(5),
				unknown(6)
				}
			MAX-ACCESS read-only
			STATUS current
			DESCRIPTION
				"Information about fan health status."
			::= { fanDescriptionEntry 4 }
			
		
		fanLocation OBJECT-TYPE
			SYNTAX DisplayString
			MAX-ACCESS read-only
			STATUS current
			DESCRIPTION
				"Fan physical location."
			::= { fanDescriptionEntry 5 } 

		
		fanFunction OBJECT-TYPE
			SYNTAX DisplayString
			MAX-ACCESS read-only
			STATUS current
			DESCRIPTION
				"Fan logic function."
			::= { fanDescriptionEntry 6 } 

		
		fanDevicename OBJECT-TYPE
			SYNTAX DisplayString
			MAX-ACCESS read-only
			STATUS current
			DESCRIPTION
				"Fan devicename."
			::= { fanDescriptionEntry 7 } 	
			
			
--    ****** FRU LED Information *******************************
  
		fruLedProperty OBJECT IDENTIFIER ::= { hwiBMC 9 }    

		fruLedDescriptionTable OBJECT-TYPE
			SYNTAX SEQUENCE OF FruLedDescriptionEntry 
			MAX-ACCESS not-accessible
			STATUS current
			DESCRIPTION
				"A table containing the list of led information."
			::= { fruLedProperty 50 }
        
                fruLedDescriptionEntry OBJECT-TYPE
			SYNTAX FruLedDescriptionEntry
			MAX-ACCESS not-accessible
			STATUS current
			DESCRIPTION
				"Information about led."
			INDEX { fruID, ledName }
			::= { fruLedDescriptionTable 1 }
		
		FruLedDescriptionEntry ::=
			SEQUENCE {
			    fruID
			        INTEGER,
				ledName
					DisplayString, 
				ledColorCapbilities
					DisplayString,
				ledColorInLocalControlState
					DisplayString,
				ledColorInOverrideState
					DisplayString,
				ledColor
					DisplayString,
				ledMode
					INTEGER,
				ledStatus
					INTEGER,
				ledLitOnLastTime
					INTEGER,
				ledLitOffLastTime
					INTEGER
				}
				 

		fruID OBJECT-TYPE	
			SYNTAX INTEGER
			MAX-ACCESS not-accessible
			STATUS current
			DESCRIPTION
				"FRU Led index."
			::= { fruLedDescriptionEntry 1 }
		

		ledName OBJECT-TYPE	
			SYNTAX DisplayString
			MAX-ACCESS read-only
			STATUS current
			DESCRIPTION
				"FRU Led name."
			::= { fruLedDescriptionEntry 2 } 
			

		ledColorCapbilities OBJECT-TYPE
			SYNTAX DisplayString
			MAX-ACCESS read-only
			STATUS current
			DESCRIPTION
				"Led capbility: BLUE,RED,GREEN,AMBER,ORANGE,WHITE.
				Return value seprate by ','."
			::= { fruLedDescriptionEntry 3 }
			

		ledColorInLocalControlState OBJECT-TYPE
			SYNTAX DisplayString
			MAX-ACCESS read-only
			STATUS current
			DESCRIPTION
				"Led control state: BLUE,RED,GREEN,AMBER,ORANGE,WHITE."
			::= { fruLedDescriptionEntry 4 }
			

		ledColorInOverrideState OBJECT-TYPE
			SYNTAX DisplayString
			MAX-ACCESS read-only
			STATUS current
			DESCRIPTION
				"Led override: BLUE,RED,GREEN,AMBER,ORANGE,WHITE."
			::= { fruLedDescriptionEntry 5 }


		ledColor OBJECT-TYPE
			SYNTAX DisplayString 
			MAX-ACCESS read-only
			STATUS current
			DESCRIPTION
				"Led color now: BLUE,RED,GREEN,AMBER,ORANGE,WHITE."
			::= { fruLedDescriptionEntry 6 }


		ledMode OBJECT-TYPE
			SYNTAX INTEGER 
				{
				localControl(1),
				override(2),
				test(3)
				}
			MAX-ACCESS read-only
			STATUS current
			DESCRIPTION
				"Information about LED mode."
			::= { fruLedDescriptionEntry 7 } 
			

		ledStatus OBJECT-TYPE
			SYNTAX INTEGER 
				{
				off(1),
				on(2),
				blinking(3)
				}
			MAX-ACCESS read-only
			STATUS current
			DESCRIPTION
				"Information LED status now."
			::= { fruLedDescriptionEntry 8 } 


		ledLitOnLastTime OBJECT-TYPE
			SYNTAX INTEGER 
			MAX-ACCESS read-only
			STATUS current
			DESCRIPTION
				"Unit:10ms(Blinking),100ms(Test)
				 Range:(1~250)*10ms(Blinking),
				       (1~127)*100ms(Test)."
			::= { fruLedDescriptionEntry 9 } 


		ledLitOffLastTime OBJECT-TYPE
			SYNTAX INTEGER 
			MAX-ACCESS read-only
			STATUS current
			DESCRIPTION
				"Unit:10ms(Blinking)
				Range:(1~250)*10ms(Blinking)."
			::= { fruLedDescriptionEntry 10 } 
			

--    ****** Component Information *******************************
  
		componentProperty OBJECT IDENTIFIER ::= { hwiBMC 10 }    

		componentDescriptionTable OBJECT-TYPE
			SYNTAX SEQUENCE OF ComponentDescriptionEntry 
			MAX-ACCESS not-accessible
			STATUS current
			DESCRIPTION
				"A table containing the part component."
			::= { componentProperty 50 }
        
                componentDescriptionEntry OBJECT-TYPE
			SYNTAX ComponentDescriptionEntry
			MAX-ACCESS not-accessible
			STATUS current
			DESCRIPTION
				"Information about led."
			INDEX { componentName }
			::= { componentDescriptionTable 1 }
		
		ComponentDescriptionEntry ::=
			SEQUENCE {				
				componentName
					DisplayString, 
				componentType
					INTEGER,
				componentPCBVersion
					DisplayString,
				componentBoardID
					DisplayString,
				componentStatus
					INTEGER
				}
	

		componentName OBJECT-TYPE	
			SYNTAX DisplayString
			MAX-ACCESS read-only
			STATUS current
			DESCRIPTION
				"Information about component name."
			::= { componentDescriptionEntry 1 } 
			

		componentType OBJECT-TYPE
			SYNTAX INTEGER
				{
				baseBoard(1),
				mezzCard(2),
				amcController(3),
				mmcController(4),
				hddBackPlane(5),
				raidCard(6),
				riserCard(9),
				lomCard(13),
				pcieCard(14)
				}
			MAX-ACCESS read-only
			STATUS current
			DESCRIPTION
				"Information about component type."
			::= { componentDescriptionEntry 2 }
			

		componentPCBVersion OBJECT-TYPE
			SYNTAX DisplayString
			MAX-ACCESS read-only
			STATUS current
			DESCRIPTION
				"Information about PCB version."
			::= { componentDescriptionEntry 3 }

			

		componentBoardID OBJECT-TYPE
			SYNTAX DisplayString
			MAX-ACCESS read-only
			STATUS current
			DESCRIPTION
				"Information about board ID."
			::= { componentDescriptionEntry 4 } 


		componentStatus OBJECT-TYPE
			SYNTAX INTEGER 
				{
				ok(1),
				minor(2),
				major(3),
				critical(4),
				absence(5),
				unknown(6)
				}
			MAX-ACCESS read-only
			STATUS current
			DESCRIPTION
				"Information about board health status."
			::= { componentDescriptionEntry 5 }		
			
			
--    ****** Firmware Information *******************************
  
		firmwareProperty OBJECT IDENTIFIER ::= { hwiBMC 11 }    

		firmwareDescriptionTable OBJECT-TYPE
			SYNTAX SEQUENCE OF FirmwareDescriptionEntry 
			MAX-ACCESS not-accessible
			STATUS current
			DESCRIPTION
				"A table containing the part firmware."
			::= { firmwareProperty 50 }
        
                firmwareDescriptionEntry OBJECT-TYPE
			SYNTAX FirmwareDescriptionEntry
			MAX-ACCESS not-accessible
			STATUS current
			DESCRIPTION
				"Information about firmware."
			INDEX { firmwareName }
			::= { firmwareDescriptionTable 1 }
		
		FirmwareDescriptionEntry ::=
			SEQUENCE {
				fruNumber
					INTEGER,
				firmwareName
					DisplayString, 
				firmwareType
					INTEGER,
				firmwareReleaseDate
					DisplayString,
				firmwareVersion
					DisplayString,
				firmwareLocation
					DisplayString,
				firmwareBoard
					DisplayString
				} 
				

		firmwareName OBJECT-TYPE	
			SYNTAX DisplayString
			MAX-ACCESS read-only
			STATUS current
			DESCRIPTION
				"Information about firmware name."
			::= { firmwareDescriptionEntry 1 } 
			

		firmwareType OBJECT-TYPE
			SYNTAX INTEGER
				{
				iBMC(1),
				fpga(2),
				cpld(3),
				bios(4),
				uboot(5),
				lcd(6)
				}
			MAX-ACCESS read-only
			STATUS current
			DESCRIPTION
				"Information about firmware type."
			::= { firmwareDescriptionEntry 2 }
			

		firmwareReleaseDate OBJECT-TYPE
			SYNTAX DisplayString
			MAX-ACCESS read-only
			STATUS current
			DESCRIPTION
				"Information about firmware release date."
			::= { firmwareDescriptionEntry 3 }

			

		firmwareVersion OBJECT-TYPE
			SYNTAX DisplayString
			MAX-ACCESS read-only
			STATUS current
			DESCRIPTION
				"Information about firmware version."
			::= { firmwareDescriptionEntry 4 }     
			

		firmwareLocation OBJECT-TYPE
			SYNTAX DisplayString
			MAX-ACCESS read-only
			STATUS current
			DESCRIPTION
				"Information about firmware location."
			::= { firmwareDescriptionEntry 5 }  
			                                                     
		fruNumber OBJECT-TYPE	
			SYNTAX INTEGER
			MAX-ACCESS not-accessible
			STATUS current
			DESCRIPTION
				"Information about FRU id."
			::= { firmwareDescriptionEntry 6 }
			

		firmwareBoard OBJECT-TYPE
			SYNTAX DisplayString
			MAX-ACCESS read-only
			STATUS current
			DESCRIPTION
				"Information about firmware Board."
			::= { firmwareDescriptionEntry 7 }
--    ****** Network Information *******************************
  
		networkProperty OBJECT IDENTIFIER ::= { hwiBMC 12 }    

		networkDescriptionTable OBJECT-TYPE
			SYNTAX SEQUENCE OF NetworkDescriptionEntry 
			MAX-ACCESS not-accessible
			STATUS current
			DESCRIPTION
				"A table containing the ethernet."
			::= { networkProperty 50 }
        
                networkDescriptionEntry OBJECT-TYPE
			SYNTAX NetworkDescriptionEntry
			MAX-ACCESS not-accessible
			STATUS current
			DESCRIPTION
				"Information about ethernet."
			INDEX { ethNum }
			::= { networkDescriptionTable 1 }
		
		NetworkDescriptionEntry ::=
			SEQUENCE {
				ethNum
					INTEGER, 
				ethIPAddress
					IpAddress,
				ethNetmask
					IpAddress,
				ethDefaultGateway
					IpAddress,
				ethIPSource
					INTEGER,
				ethMACAddress
					DisplayString,
				ethType
					INTEGER,
				ethHostPort
					INTEGER,
				ethEnable
					INTEGER,
				ethMode
					INTEGER,
				vlanID
					DisplayString,
				ethInfo
					DisplayString,
				ethIPv4Enable
					INTEGER
				}
				 

		ethNum OBJECT-TYPE	
			SYNTAX INTEGER
			MAX-ACCESS not-accessible
			STATUS current
			DESCRIPTION
				"Information about ethernet port number."
			::= { networkDescriptionEntry 1 } 
			

		ethIPAddress OBJECT-TYPE
			SYNTAX IpAddress
			MAX-ACCESS read-write
			STATUS current
			DESCRIPTION
				"Information about ethernet IP address."
			::= { networkDescriptionEntry 2 }
			

		ethNetmask OBJECT-TYPE
			SYNTAX IpAddress
			MAX-ACCESS read-write
			STATUS current
			DESCRIPTION
				"Information about netmask."
			::= { networkDescriptionEntry 3 }

			

		ethDefaultGateway OBJECT-TYPE
			SYNTAX IpAddress
			MAX-ACCESS read-write
			STATUS current
			DESCRIPTION
				"Information about default gateway."
			::= { networkDescriptionEntry 4 }  



		ethIPSource OBJECT-TYPE
			SYNTAX INTEGER 
				{
				static(1),
				dhcp(2)
				}
			MAX-ACCESS read-write
			STATUS current
			DESCRIPTION
				"Information about IP source."
			::= { networkDescriptionEntry 5 }  	
			

		ethMACAddress OBJECT-TYPE
			SYNTAX DisplayString 
			MAX-ACCESS read-only
			STATUS current
			DESCRIPTION
				"Information about MAC address."
			::= { networkDescriptionEntry 6 }
			

		ethType OBJECT-TYPE
			SYNTAX INTEGER 
				{
				mgmt(1),
				share(2)
				}
			MAX-ACCESS read-only
			STATUS current
			DESCRIPTION
				"Information about ethernet port type."
			::= { networkDescriptionEntry 7 }
			

		ethHostPort OBJECT-TYPE
			SYNTAX INTEGER 
				{
				none(1),
				port1(2),
				port2(3),
				port3(4),
				port4(5)
				}
			MAX-ACCESS read-write
			STATUS current
			DESCRIPTION
				"Information about share ethernet binded host port."
			::= { networkDescriptionEntry 8 }       
			

		ethEnable OBJECT-TYPE
			SYNTAX INTEGER
			{
				disable(1),
				enable(2)
			}
			MAX-ACCESS read-write
			STATUS obsolete
			DESCRIPTION
				"Information about eth enabled."
			::= { networkDescriptionEntry 9 } 			
			

		ethMode OBJECT-TYPE
			SYNTAX INTEGER 
				{
				dedicated (1),
				lomShare(2),
				adaptive(3),
				pcieShare(4)
				}
			MAX-ACCESS read-write
			STATUS current
			DESCRIPTION
				"Information about ethernet Mode."
			::= { networkDescriptionEntry 10 }		
	

		vlanID OBJECT-TYPE
			SYNTAX DisplayString 
			MAX-ACCESS read-write
			STATUS current
			DESCRIPTION
				"Disable or enable VLAN and set ID.
				 Set 'off' to disabled VLAN.
				 Set [1,4094] to enable VLAN and set ID."
			::= { networkDescriptionEntry 11 }
		
        
		ethInfo OBJECT-TYPE
			SYNTAX DisplayString 
			MAX-ACCESS read-write
			STATUS current
			DESCRIPTION
				"Set IPaddr,Netmask,Gateway.
				eg.: 192.168.2.100,255.255.255.0,192.168.2.1"
			::= { networkDescriptionEntry 12 }

		ethIPv4Enable OBJECT-TYPE
			SYNTAX INTEGER
			{
				disable(1),
				enable(2)
			}
			MAX-ACCESS read-write
			STATUS current
			DESCRIPTION
				"Information about eth IPv4 enabled."
			::= { networkDescriptionEntry 13 }
			
--    ****** Sensor Information *******************************
  
		sensorProperty OBJECT IDENTIFIER ::= { hwiBMC 13 }    

		sensorDescriptionTable OBJECT-TYPE
			SYNTAX SEQUENCE OF SensorDescriptionEntry 
			MAX-ACCESS not-accessible
			STATUS current
			DESCRIPTION
				"A table containing the sensor."
			::= { sensorProperty 50 }
        
                sensorDescriptionEntry OBJECT-TYPE
			SYNTAX SensorDescriptionEntry
			MAX-ACCESS not-accessible
			STATUS current
			DESCRIPTION
				"Information about sensor."
			INDEX { sensorName }
			::= { sensorDescriptionTable 1 }
		
		SensorDescriptionEntry ::=
			SEQUENCE {
				sensorName
					DisplayString, 
				sensorReading
					DisplayString,
				sensorUpperNonRecoverable
					DisplayString,
				sensorUpperCritical
					DisplayString,
				sensorUpperMinor
					DisplayString,
				sensorLowerNonRecoverable
					DisplayString,
				sensorLowerCritical
					DisplayString,
				sensorLowerMinor
					DisplayString, 
				sensorStatus
					DisplayString,
				sensorType
					INTEGER,
				sensorPositiveHysteresis
					INTEGER,
				sensorNegativeHysteresis					
				    INTEGER,
				sensorPositiveHysteresisString
					DisplayString,
				sensorNegativeHysteresisString					
				    DisplayString,
				sensorUnit
					INTEGER,
				sensorEventReadingType
				INTEGER
				}


		sensorName OBJECT-TYPE	
			SYNTAX DisplayString
			MAX-ACCESS read-only
			STATUS current
			DESCRIPTION
				"Information about sensor name."
			::= { sensorDescriptionEntry 1 } 
			

		sensorReading OBJECT-TYPE
			SYNTAX DisplayString
			MAX-ACCESS read-only
			STATUS current
			DESCRIPTION
				"Sensor current reading."
			::= { sensorDescriptionEntry 2 }
			

		sensorUpperNonRecoverable OBJECT-TYPE
			SYNTAX DisplayString
			MAX-ACCESS read-only
			STATUS current
			DESCRIPTION
				"Information about sensor upper nonrecoverable threshold."
			::= { sensorDescriptionEntry 3 }

			

		sensorUpperCritical OBJECT-TYPE
			SYNTAX DisplayString
			MAX-ACCESS read-only
			STATUS current
			DESCRIPTION
				"Information about sensor upper crtical threshold."
			::= { sensorDescriptionEntry 4 }  



		sensorUpperMinor OBJECT-TYPE
			SYNTAX DisplayString 
			MAX-ACCESS read-only
			STATUS current
			DESCRIPTION
				"Information about sensor upper minor threshold."
			::= { sensorDescriptionEntry 5 }  	
			

		sensorLowerNonRecoverable OBJECT-TYPE
			SYNTAX DisplayString 
			MAX-ACCESS read-only
			STATUS current
			DESCRIPTION
				"Information about sensor lower nonrecoverable threshold."
			::= { sensorDescriptionEntry 6 } 



		sensorLowerCritical OBJECT-TYPE
			SYNTAX DisplayString 
			MAX-ACCESS read-only
			STATUS current
			DESCRIPTION
				"Information about sensor lower crtical threshold."
			::= { sensorDescriptionEntry 7 } 
			

		sensorLowerMinor OBJECT-TYPE
			SYNTAX DisplayString 
			MAX-ACCESS read-only
			STATUS current
			DESCRIPTION
				"Information about sensor lower minor threshold."
			::= { sensorDescriptionEntry 8 } 
			
			

		sensorStatus OBJECT-TYPE
			SYNTAX DisplayString 
			MAX-ACCESS read-only
			STATUS current
			DESCRIPTION
				"Information about sensor status."
			::= { sensorDescriptionEntry 9 } 
			

		sensorType OBJECT-TYPE
			SYNTAX INTEGER 
			MAX-ACCESS read-only
			STATUS current
			DESCRIPTION
				"Information about sensor type."
			::= { sensorDescriptionEntry 10 } 		
			

		sensorPositiveHysteresis OBJECT-TYPE
			SYNTAX INTEGER 
			MAX-ACCESS read-only
			STATUS current
			DESCRIPTION
				"Positive-going Threshold Hysteresis Value. Set to 00h if sensor does not 
				support positive-going threshold hysteresis. This value is subtracted from 
				positive going thresholds to determine the point where the asserted status for 
				that threshold will clear. See section 35.13.2, Hysteresis and Event Status and 
				section 35.13.3, High-going versus Low-going Threshold Events.  "
			::= { sensorDescriptionEntry 11 }	


		sensorNegativeHysteresis OBJECT-TYPE
			SYNTAX INTEGER 
			MAX-ACCESS read-only
			STATUS current
			DESCRIPTION
				"Negative-going Threshold Hysteresis Value. This value is added  to negative 
				going thresholds to determine the point where the asserted status for that 
				threshold will clear. Set to 00h if sensor does not support negative-going 
				threshold hysteresis. "
			::= { sensorDescriptionEntry 12 }			
			

		sensorPositiveHysteresisString OBJECT-TYPE
			SYNTAX DisplayString 
			MAX-ACCESS read-only
			STATUS current
			DESCRIPTION
				"Positive-going Threshold Hysteresis Value. Set to 'na' if sensor does not 
				support positive-going threshold hysteresis. This value is subtracted from 
				positive going thresholds to determine the point where the asserted status for 
				that threshold will clear. See section 35.13.2, Hysteresis and Event Status and 
				section 35.13.3, High-going versus Low-going Threshold Events.  "
			::= { sensorDescriptionEntry 13 }	


		sensorNegativeHysteresisString  OBJECT-TYPE
			SYNTAX DisplayString 
			MAX-ACCESS read-only
			STATUS current
			DESCRIPTION
				"Negative-going Threshold Hysteresis Value. This value is added  to negative 
				going thresholds to determine the point where the asserted status for that 
				threshold will clear. Set to 'na' if sensor does not support negative-going 
				threshold hysteresis. "
			::= { sensorDescriptionEntry 14 }
        
        sensorUnit OBJECT-TYPE
			SYNTAX INTEGER 
					{
					unspecified (0),
					degrees-c (1),
					degrees-f (2),
					degrees-k (3),
					volts (4),
					amps (5),
					watts (6),
					rpm (18)				
					}
			MAX-ACCESS read-only
			STATUS current
			DESCRIPTION
				"Information about sensor unit."
			::= { sensorDescriptionEntry 15 } 

        sensorEventReadingType OBJECT-TYPE
			SYNTAX INTEGER 
			MAX-ACCESS read-only
			STATUS current
			DESCRIPTION
				"Information about event reading type."
			::= { sensorDescriptionEntry 16 } 			
			
--    ****** Local User Information *******************************
  
		userProperty OBJECT IDENTIFIER ::= { hwiBMC 14 }    

		userDescriptionTable OBJECT-TYPE
			SYNTAX SEQUENCE OF UserDescriptionEntry 
			MAX-ACCESS not-accessible
			STATUS current
			DESCRIPTION
				"A table containing the user."
			::= { userProperty 50 }
        
                userDescriptionEntry OBJECT-TYPE
			SYNTAX UserDescriptionEntry
			MAX-ACCESS not-accessible
			STATUS current
			DESCRIPTION
				"Information about user."
			INDEX { userID }
			::= { userDescriptionTable 1 }
		
		UserDescriptionEntry ::=
			SEQUENCE {
				userID
					INTEGER, 
				userEnable
					INTEGER,
				userName
					DisplayString,
				userPassword
					DisplayString,
				userGroupID
					INTEGER,
				userDelete
				    INTEGER,
				userInterfaces
				    INTEGER,
				userPublicKeyAdd
					DisplayString,
				userPublicKeyDelete
					DisplayString,
				userPublicKeyHash
					DisplayString
				}
				 

		userID OBJECT-TYPE	
			SYNTAX INTEGER
			MAX-ACCESS not-accessible
			STATUS current
			DESCRIPTION
				"Information about user id, the vaule is in [2, 17]."
			::= { userDescriptionEntry 1 } 
			

		userEnable OBJECT-TYPE
			SYNTAX INTEGER
				{
				disable(1),
				enable(2)
				}
			MAX-ACCESS read-write
			STATUS current
			DESCRIPTION
				"Information about user enable status , disable 1, enable 2.
				Default value is disable(1)."
			::= { userDescriptionEntry 2 }
			

		userName OBJECT-TYPE
			SYNTAX DisplayString
			MAX-ACCESS read-write
			STATUS current
			DESCRIPTION
				"User name length is 1 to 16 characters.
				The value can contain letters, digits, and special characters. The value cannot contain spaces, double quotation and the following special characters: , \ : < > & ' / %, and cannot start with a number sign (#)."
			::= { userDescriptionEntry 3 }


		userPassword OBJECT-TYPE
			SYNTAX DisplayString
			MAX-ACCESS read-write
			STATUS current
			DESCRIPTION
				"Information about user password. User password length is 1 to 20 characters."
			::= { userDescriptionEntry 4 }  


		userGroupID OBJECT-TYPE
			SYNTAX INTEGER 
			{
				commonUser(1),
				operator(2),
				administrator(3),
				noAccess(4),
				customRole1(5),
				customRole2(6),
				customRole3(7),
				customRole4(8)
			}
			MAX-ACCESS read-write
			STATUS current
			DESCRIPTION
				"Information about user group.
				When set, this vaule will be one of the following:(1, 2, 3, 5, 6, 7, 8).
				1 - common user
				2 - operator 
				3 - administrator  
				4 - no access(only for get)
				5 - custom role1
				6 - custom role2 
				7 - custom role3  
				8 - custom role4."
			::= { userDescriptionEntry 5 }  
			

		userDelete OBJECT-TYPE
			SYNTAX INTEGER 
			{
				delete(1)
			}
			MAX-ACCESS read-write
			STATUS current
			DESCRIPTION
				"Information about delete user.
				This vaule will be one of the following:
				(delete(1))."
			::= { userDescriptionEntry 6 } 	
			
		userInterfaces OBJECT-TYPE
			SYNTAX INTEGER
			MAX-ACCESS read-write
			STATUS current
			DESCRIPTION
				"Information about user login interfaces.
				bit0 - Web:    0 disabled; 1 enabled
				bit1 - SNMP:   0 disabled; 1 enabled
				bit2 - IPMI:   0 disabled; 1 enabled
				bit3 - SSH:    0 disabled; 1 enabled
				bit4 - SFTP:   0 disabled; 1 enabled
				bit6 - Local:  0 disabled; 1 enabled
				bit7 - Redfish:0 disabled; 1 enabled"
			::= { userDescriptionEntry 7 }
			
		userPublicKeyAdd OBJECT-TYPE
			SYNTAX DisplayString
			MAX-ACCESS read-write
			STATUS current
			DESCRIPTION
				"Add PublicKey, the set format is: <publickey file>, with max length 256."
			::= { userDescriptionEntry 8 }  
			
		userPublicKeyDelete OBJECT-TYPE
			SYNTAX DisplayString
			MAX-ACCESS read-write
			STATUS current
			DESCRIPTION
				"Delete PublicKey"
			::= { userDescriptionEntry 9 }  
			
		userPublicKeyHash OBJECT-TYPE
			SYNTAX DisplayString
			MAX-ACCESS read-only
			STATUS current
			DESCRIPTION
				"PublicKey Hash"
			::= { userDescriptionEntry 10 }  

--    ****** CPU Information *******************************
  
		cpuProperty OBJECT IDENTIFIER ::= { hwiBMC 15 }    
		

		cpuEntireStatus OBJECT-TYPE
			SYNTAX INTEGER 
				{
				ok(1),
				minor(2),
				major(3),
				critical(4),
				absence(5),
				unknown(6)
				}
			MAX-ACCESS read-only
			STATUS current
			DESCRIPTION
				"Information about all cpu health status."
			::= { cpuProperty 1 }
			
		cpuDescriptionTable OBJECT-TYPE
			SYNTAX SEQUENCE OF CPUDescriptionEntry 
			MAX-ACCESS not-accessible
			STATUS current
			DESCRIPTION
				"A table containing the CPU information."
			::= { cpuProperty 50 }
        
                cpuDescriptionEntry OBJECT-TYPE
			SYNTAX CPUDescriptionEntry
			MAX-ACCESS not-accessible
			STATUS current
			DESCRIPTION
				"Information about CPU."
			INDEX { cpuIndex }
			::= { cpuDescriptionTable 1 }
		
		CPUDescriptionEntry ::=
			SEQUENCE {
				cpuIndex
					INTEGER, 
				cpuManufacturer
					DisplayString,
				cpuFamily
					DisplayString,
				cpuType
					DisplayString,
				cpuClockRate
					DisplayString,
				cpuStatus
					INTEGER,
				cpuAvailability
				        INTEGER,
				cpuLocation
					DisplayString,
				cpuFunction
					DisplayString,
				cpuDevicename
					DisplayString,
				cpuProcessorID
					DisplayString,
				cpuCoreCount
					INTEGER,
				cpuThreadCount
					INTEGER,
				cpuMemoryTechnology
					DisplayString,
				cpuL1Cache-K
					INTEGER,
				cpuL2Cache-K
					INTEGER,
				cpuL3Cache-K
					INTEGER
				}
				 

		cpuIndex OBJECT-TYPE	
			SYNTAX INTEGER
			MAX-ACCESS not-accessible
			STATUS current
			DESCRIPTION
				"Information about CPU index."
			::= { cpuDescriptionEntry 1 } 
			

		cpuManufacturer OBJECT-TYPE
			SYNTAX DisplayString
			MAX-ACCESS read-only
			STATUS current
			DESCRIPTION
				"Information about CPU manufacturer."
			::= { cpuDescriptionEntry 2 }
			

		cpuFamily OBJECT-TYPE
			SYNTAX DisplayString
			MAX-ACCESS read-only
			STATUS current
			DESCRIPTION
				"Information about CPU family."
			::= { cpuDescriptionEntry 3 }

			

		cpuType OBJECT-TYPE
			SYNTAX DisplayString
			MAX-ACCESS read-only
			STATUS current
			DESCRIPTION
				"Information about CPU type."
			::= { cpuDescriptionEntry 4 }  



		cpuClockRate OBJECT-TYPE
			SYNTAX DisplayString 
			MAX-ACCESS read-only
			STATUS current
			DESCRIPTION
				"Information about CPU clock rate."
			::= { cpuDescriptionEntry 5 }  	
			
			

		cpuStatus OBJECT-TYPE
			SYNTAX INTEGER 
				{
				ok(1),
				minor(2),
				major(3),
				critical(4),
				absence(5),
				unknown(6)
				}
			MAX-ACCESS read-only
			STATUS current
			DESCRIPTION
				"Information about CPU health status."
			::= { cpuDescriptionEntry 6 }
		
		

		cpuAvailability OBJECT-TYPE
			SYNTAX INTEGER 
				{
				unknown(1),
				disabled(2),
				backup(3),
				active(4)
				}
			MAX-ACCESS read-only
			STATUS current
			DESCRIPTION
				"Information about CPU availability."
			::= { cpuDescriptionEntry 7 } 
		
		
		cpuLocation OBJECT-TYPE
			SYNTAX DisplayString 
			MAX-ACCESS read-only
			STATUS current
			DESCRIPTION
				"CPU physical location."
			::= { cpuDescriptionEntry 8 }  	

        
		cpuFunction OBJECT-TYPE
			SYNTAX DisplayString 
			MAX-ACCESS read-only
			STATUS current
			DESCRIPTION
				"CPU logic function."
			::= { cpuDescriptionEntry 9 }  	

        
		cpuDevicename OBJECT-TYPE
			SYNTAX DisplayString 
			MAX-ACCESS read-only
			STATUS current
			DESCRIPTION
				"CPU devicename."
			::= { cpuDescriptionEntry 10 }  
							
		cpuProcessorID OBJECT-TYPE
			SYNTAX DisplayString 
			MAX-ACCESS read-only
			STATUS current
			DESCRIPTION
				"CPU ProcessorID."
			::= { cpuDescriptionEntry 11 }
			
		cpuCoreCount OBJECT-TYPE
			SYNTAX INTEGER 
			MAX-ACCESS read-only
			STATUS current
			DESCRIPTION
				"CPU CoreCount."
			::= { cpuDescriptionEntry 12 }  
			
		cpuThreadCount OBJECT-TYPE
			SYNTAX INTEGER 
			MAX-ACCESS read-only
			STATUS current
			DESCRIPTION
				"CPU ThreadCount."
			::= { cpuDescriptionEntry 13 }  
			
		cpuMemoryTechnology OBJECT-TYPE
			SYNTAX DisplayString 
			MAX-ACCESS read-only
			STATUS current
			DESCRIPTION
				"CPU memory technology."
			::= { cpuDescriptionEntry 14 }  
			
		cpuL1Cache-K OBJECT-TYPE
			SYNTAX INTEGER 
			MAX-ACCESS read-only
			STATUS current
			DESCRIPTION
				"CPU Cache."
			::= { cpuDescriptionEntry 15 }
			
		cpuL2Cache-K OBJECT-TYPE
			SYNTAX INTEGER 
			MAX-ACCESS read-only
			STATUS current
			DESCRIPTION
				"CPU Cache."
			::= { cpuDescriptionEntry 16 }
			
		cpuL3Cache-K OBJECT-TYPE
			SYNTAX INTEGER 
			MAX-ACCESS read-only
			STATUS current
			DESCRIPTION
				"CPU Cache."
			::= { cpuDescriptionEntry 17 }
--    ****** Memory Information *******************************
  
		memoryProperty OBJECT IDENTIFIER ::= { hwiBMC 16 }
		

		memoryEntireStatus OBJECT-TYPE
			SYNTAX INTEGER 
				{
				ok(1),
				minor(2),
				major(3),
				critical(4),
				absence(5),
				unknown(6)
				}
			MAX-ACCESS read-only
			STATUS current
			DESCRIPTION
				"Information about all memory health status."
			::= { memoryProperty 1 }     

		memoryDescriptionTable OBJECT-TYPE
			SYNTAX SEQUENCE OF MemoryDescriptionEntry 
			MAX-ACCESS not-accessible
			STATUS current
			DESCRIPTION
				"A table containing the memory."
			::= { memoryProperty 50 }
        
                memoryDescriptionEntry OBJECT-TYPE
			SYNTAX MemoryDescriptionEntry
			MAX-ACCESS not-accessible
			STATUS current
			DESCRIPTION
				"Information about memory."
			INDEX { memoryDimmIndex }
			::= { memoryDescriptionTable 1 }
		
		MemoryDescriptionEntry ::=
			SEQUENCE {
				memoryDimmIndex
					INTEGER, 
				memoryLogic
					DisplayString,
				memoryManufacturer
					DisplayString,
				memorySize
					DisplayString,
				memoryClockRate
					DisplayString,
				memoryStatus
					INTEGER,
				memoryAvailability 
					INTEGER,
				memoryLocation
					DisplayString,
				memoryFunction
					DisplayString,
				memoryDevicename
					DisplayString,
				memoryType
					DisplayString,
				memorySN
					DisplayString,
				memoryMinimumVoltage
					INTEGER,
				memoryRank
					INTEGER,
				memoryBitWidth
					INTEGER,
				memoryTechnology
					DisplayString
				}
				 

		memoryDimmIndex OBJECT-TYPE	
			SYNTAX INTEGER
			MAX-ACCESS not-accessible
			STATUS current
			DESCRIPTION
				"Information about memory DIMM index."
			::= { memoryDescriptionEntry 1 } 
			

		memoryLogic OBJECT-TYPE
			SYNTAX DisplayString
			MAX-ACCESS read-only
			STATUS current
			DESCRIPTION
				"Information about memory logic channel."
			::= { memoryDescriptionEntry 2 }
			

		memoryManufacturer OBJECT-TYPE
			SYNTAX DisplayString
			MAX-ACCESS read-only
			STATUS current
			DESCRIPTION
				"Information about memory manufacturer."
			::= { memoryDescriptionEntry 3 }


		memorySize OBJECT-TYPE
			SYNTAX DisplayString
			MAX-ACCESS read-only
			STATUS current
			DESCRIPTION
				"Information about memory capacity."
			::= { memoryDescriptionEntry 4 }  


		memoryClockRate OBJECT-TYPE
			SYNTAX DisplayString 
			MAX-ACCESS read-only
			STATUS current
			DESCRIPTION
				"Information about memory clock rate."
			::= { memoryDescriptionEntry 5 }
			

		memoryStatus OBJECT-TYPE
			SYNTAX INTEGER 
				{
				ok(1),
				minor(2),
				major(3),
				critical(4),
				absence(5),
				unknown(6)
				}
			MAX-ACCESS read-only
			STATUS current
			DESCRIPTION
				"Information about memory health status."
			::= { memoryDescriptionEntry 6 }  	
		

		memoryAvailability OBJECT-TYPE
			SYNTAX INTEGER 
				{
				unknown(1),
				disabled(2),
				backup(3),
				active(4)
				}
			MAX-ACCESS read-only
			STATUS current
			DESCRIPTION
				"Information about memory availability."
			::= { memoryDescriptionEntry 7 } 
			
		memoryLocation OBJECT-TYPE
			SYNTAX DisplayString 
			MAX-ACCESS read-only
			STATUS current
			DESCRIPTION
				"Memory physical location."
			::= { memoryDescriptionEntry 8 }
			
		
		memoryFunction OBJECT-TYPE
			SYNTAX DisplayString 
			MAX-ACCESS read-only
			STATUS current
			DESCRIPTION
				"Memory logic function."
			::= { memoryDescriptionEntry 9 }

		
		memoryDevicename OBJECT-TYPE
			SYNTAX DisplayString 
			MAX-ACCESS read-only
			STATUS current
			DESCRIPTION
				"Memory devicename."
			::= { memoryDescriptionEntry 10 }

		memoryType OBJECT-TYPE
			SYNTAX DisplayString
			MAX-ACCESS read-only
			STATUS current
			DESCRIPTION
				"Information about memory type."
			::= { memoryDescriptionEntry 11 }  
			
		memorySN OBJECT-TYPE
			SYNTAX DisplayString
			MAX-ACCESS read-only
			STATUS current
			DESCRIPTION
				"Information about memory SN."
			::= { memoryDescriptionEntry 12 }  
			
		memoryMinimumVoltage OBJECT-TYPE
			SYNTAX INTEGER
			MAX-ACCESS read-only
			STATUS current
			DESCRIPTION
				"Information about memory minimum voltage."
			::= { memoryDescriptionEntry 13 }  

		memoryRank OBJECT-TYPE
			SYNTAX INTEGER
			MAX-ACCESS read-only
			STATUS current
			DESCRIPTION
				"Information about memory rank."
			::= { memoryDescriptionEntry 14 }  
			
		memoryBitWidth OBJECT-TYPE
			SYNTAX INTEGER
			MAX-ACCESS read-only
			STATUS current
			DESCRIPTION
				"Information about memory bit width."
			::= { memoryDescriptionEntry 15 }  

		memoryTechnology OBJECT-TYPE
			SYNTAX DisplayString
			MAX-ACCESS read-only
			STATUS current
			DESCRIPTION
				"Information about memory technology."
			::= { memoryDescriptionEntry 16 }  
			
--    ****** LOM(LAN on motherboard) Information *******************************
  
		lomProperty OBJECT IDENTIFIER ::= { hwiBMC 17 }    

		lomDescriptionTable OBJECT-TYPE
			SYNTAX SEQUENCE OF LOMDescriptionEntry 
			MAX-ACCESS not-accessible
			STATUS current
			DESCRIPTION
				"A table containing the LOM."
			::= { lomProperty 50 }
        
                lomDescriptionEntry OBJECT-TYPE
			SYNTAX LOMDescriptionEntry
			MAX-ACCESS not-accessible
			STATUS current
			DESCRIPTION
				"Information about LOM."
			INDEX { lomIndex }
			::= { lomDescriptionTable 1 }
		
		LOMDescriptionEntry ::=
			SEQUENCE {
				lomIndex
					INTEGER, 
				lomMACAddress
					DisplayString
				}
				 

		lomIndex OBJECT-TYPE	
			SYNTAX INTEGER
			MAX-ACCESS not-accessible
			STATUS current
			DESCRIPTION
				"Information about LOM index."
			::= { lomDescriptionEntry 1 } 
			

		lomMACAddress OBJECT-TYPE
			SYNTAX DisplayString
			MAX-ACCESS read-only
			STATUS current
			DESCRIPTION
				"Information about LOM MAC address."
			::= { lomDescriptionEntry 2 }


--    ****** HardDisk Information *******************************
  
		hardDiskProperty OBJECT IDENTIFIER ::= { hwiBMC 18 }
		

		hardDiskEntireStatus OBJECT-TYPE
			SYNTAX INTEGER 
				{
				ok(1),
				minor(2),
				major(3),
				critical(4),
				absence(5),
				unknown(6)
				}
			MAX-ACCESS read-only
			STATUS current
			DESCRIPTION
				"Information about all hard disk health status."
			::= { hardDiskProperty 1 }    

		hardDiskDescriptionTable OBJECT-TYPE
			SYNTAX SEQUENCE OF HardDiskDescriptionEntry 
			MAX-ACCESS not-accessible
			STATUS current
			DESCRIPTION
				"A table containing the hard disk."
			::= { hardDiskProperty 50 }
        
                hardDiskDescriptionEntry OBJECT-TYPE
			SYNTAX HardDiskDescriptionEntry 
			MAX-ACCESS not-accessible
			STATUS current
			DESCRIPTION
				"Information about hard disk."
			INDEX { hardDiskIndex }
			::= { hardDiskDescriptionTable 1 }
		
		HardDiskDescriptionEntry ::=
			SEQUENCE {
				hardDiskIndex
					INTEGER, 
				hardDiskPresence
					INTEGER,
				hardDiskStatus
					INTEGER,
				hardDiskLocation
					DisplayString, 
				hardDiskFunction
					DisplayString,
				hardDiskDevicename
					DisplayString,
				hardDiskSerialNumber
					DisplayString,	
				hardDiskModelNumber
					DisplayString,	
				hardDiskManufacturer
					DisplayString,
				hardDiskFwState
					INTEGER,
				hardDiskFwVersion
					DisplayString,
				hardDiskCapacityInGB
					INTEGER,
				hardDiskMediaType
					INTEGER,
				hardDiskInterfaceType
					INTEGER,
				hardDiskPowerState
					INTEGER,
				hardDiskRebuildProgress
					INTEGER,
				hardDiskPatrolReadStatus
					INTEGER,
				hardDiskCapableSpeedInMbps
					INTEGER,
				hardDiskNegotiatedSpeedInMbps
					INTEGER,
				hardDiskTemperature
					INTEGER,
				hardDiskSASAddr1
					DisplayString,
				hardDiskSASAddr2
					DisplayString,
				hardDiskPrefailState
					INTEGER,
				hardDiskHotSpareState
					INTEGER,
				hardDiskRemnantWearout
					INTEGER,
				hardDiskMediaErrCount
					INTEGER,
				hardDiskPrefailErrCount
					INTEGER,
				hardDiskOtherErrCount
					INTEGER,
				hardDiskLocationState
					INTEGER,
				hardDiskCapacityInMB
					INTEGER				
				}
				 

		hardDiskIndex OBJECT-TYPE	
			SYNTAX INTEGER
			MAX-ACCESS not-accessible
			STATUS current
			DESCRIPTION
				"Information about hard disk index."
			::= { hardDiskDescriptionEntry 1 } 
			

		hardDiskPresence OBJECT-TYPE
			SYNTAX INTEGER
				{
				absence(1),
				presence(2),
				unknown(3)
				}
			MAX-ACCESS read-only
			STATUS current
			DESCRIPTION
				"Information about hard disk presence."
			::= { hardDiskDescriptionEntry 2 }


		hardDiskStatus OBJECT-TYPE
			SYNTAX INTEGER 
				{
				ok(1),
				minor(2),
				major(3),
				critical(4),
				absence(5),
				unknown(6)
				}
			MAX-ACCESS read-only
			STATUS current
			DESCRIPTION
				"Information about hard disk health."
			::= { hardDiskDescriptionEntry 3 }  

		hardDiskLocation OBJECT-TYPE	
			SYNTAX DisplayString
			MAX-ACCESS read-only
			STATUS current
			DESCRIPTION
				"Hard disk physical location."
			::= { hardDiskDescriptionEntry 4 } 

		
		hardDiskFunction OBJECT-TYPE	
			SYNTAX DisplayString
			MAX-ACCESS read-only
			STATUS current
			DESCRIPTION
				"Hard disk logic function."
			::= { hardDiskDescriptionEntry 5 } 

		
		hardDiskDevicename OBJECT-TYPE	
			SYNTAX DisplayString
			MAX-ACCESS read-only
			STATUS current
			DESCRIPTION
				"Hard disk devicename."
			::= { hardDiskDescriptionEntry 6 } 		

		hardDiskSerialNumber OBJECT-TYPE	
			SYNTAX DisplayString
			MAX-ACCESS read-only
			STATUS current
			DESCRIPTION
				"Hard disk serial number."
			::= { hardDiskDescriptionEntry 7 } 			

		hardDiskModelNumber OBJECT-TYPE	
			SYNTAX DisplayString
			MAX-ACCESS read-only
			STATUS current
			DESCRIPTION
				"Hard disk model number."
			::= { hardDiskDescriptionEntry 8 } 			

		hardDiskManufacturer OBJECT-TYPE	
			SYNTAX DisplayString
			MAX-ACCESS read-only
			STATUS current
			DESCRIPTION
				"Hard disk manufacturer."
			::= { hardDiskDescriptionEntry 9 }  
	
		hardDiskFwState OBJECT-TYPE	
			SYNTAX INTEGER 
				{
				unconfigured-good(1),
				unconfigured-bad(2),
				hot-spare(3),
				offline(4),
				failed(5),
				rebuild(6),
				online(7),
				copyback(8),
				jbod(9),
				unconfigured-shielded(10),
				hot-spare-shielded(11),
				configured-shielded(12),
				foreign(13),
				unknown(255)				
				}
			MAX-ACCESS read-write
			STATUS current
			DESCRIPTION
				"Hard disk firmware state.
				1: Unconfigured Good
				   Can be set from JBOD state when raidControllerJBODEnable = Enabled.
				2: Unconfigured Bad (read only)
				3: Hot Spared (read only)
				4: Offline
				   Can be set from Online state.
				5: Failed (read only)
				6: Rebuild (read only)
				7: Online
				   Can be set from Offline state.
				8: Copyback (read only)
				9: JBOD
				   Can be set from Unconfigured Good state when raidControllerJBODEnable = Enabled.
				10: Unconfigured Shielded (read only)
				11: Hot Spare Shielded (read only)
				12: Configured Shielded (read only)
				13: Foreign (read only)
				255: Unknown (read only)"
			::= { hardDiskDescriptionEntry 10 } 	
	
		hardDiskFwVersion OBJECT-TYPE	
			SYNTAX DisplayString 
			MAX-ACCESS read-only
			STATUS current
			DESCRIPTION
				"Hard disk firmware version."
			::= { hardDiskDescriptionEntry 11 } 	
	
		hardDiskCapacityInGB OBJECT-TYPE	
			SYNTAX INTEGER 
				{
				unknown(4294967295)
				}
			MAX-ACCESS read-only
			STATUS current
			DESCRIPTION
				"Hard disk capacity (GB)."
			::= { hardDiskDescriptionEntry 12 } 
	
		hardDiskMediaType OBJECT-TYPE	
			SYNTAX INTEGER 
				{
				hdd(1),
				ssd(2),
				ssm(3),
				unknown(255)
				}
			MAX-ACCESS read-only
			STATUS current
			DESCRIPTION
				"Hard disk media type."
			::= { hardDiskDescriptionEntry 13 } 	
	
		hardDiskInterfaceType OBJECT-TYPE	
			SYNTAX INTEGER 
				{
				undefined(1),
				parallel-scsi(2),
				sas(3),
				sata(4),
				fiber-channel(5),
				sata-sas(6),
				pcie(7),
				unknown(255)
				}
			MAX-ACCESS read-only
			STATUS current
			DESCRIPTION
				"Hard disk interface type. SAS, SATA...etc.
				1: Undefined
				2: Parallel-SCSI
				3: SAS
				4: SATA
				5: Fiber Channel
				6: SATA/SAS
				7: PCIe
				255: Unknown"
			::= { hardDiskDescriptionEntry 14 }	
	
		hardDiskPowerState OBJECT-TYPE	
			SYNTAX INTEGER 
				{
				spun-up(1),
				spun-down(2),
				transition(3),
				unknown(255)
				}
			MAX-ACCESS read-only
			STATUS current
			DESCRIPTION
				"Hard disk power state."
			::= { hardDiskDescriptionEntry 15 }
	
		hardDiskRebuildProgress OBJECT-TYPE	
			SYNTAX INTEGER 
				{
				unknown(255)
				}
			MAX-ACCESS read-only
			STATUS current
			DESCRIPTION
				"Hard disk rebuild progress (0 - 100%)."
			::= { hardDiskDescriptionEntry 16 }	
			
		hardDiskPatrolReadStatus OBJECT-TYPE	
			SYNTAX INTEGER 
				{
				stopped(1),
				in-progress(2),
				unknown(255)
				}
			MAX-ACCESS read-only
			STATUS current
			DESCRIPTION
				"Hard disk patrol read status."
			::= { hardDiskDescriptionEntry 17 }				
	
		hardDiskCapableSpeedInMbps OBJECT-TYPE	
			SYNTAX INTEGER 
				{
				unknown(4294967295)
				}
			MAX-ACCESS read-only
			STATUS current
			DESCRIPTION
				"Hard disk maximum supported speed."
			::= { hardDiskDescriptionEntry 18 }		
	
		hardDiskNegotiatedSpeedInMbps OBJECT-TYPE	
			SYNTAX INTEGER 
				{
				unknown(4294967295)
				}
			MAX-ACCESS read-only
			STATUS current
			DESCRIPTION
				"Hard disk negotiated speed."
			::= { hardDiskDescriptionEntry 19 }		
	
		hardDiskTemperature OBJECT-TYPE	
			SYNTAX INTEGER 
				{
				unknown(255)
				}
			MAX-ACCESS read-only
			STATUS current
			DESCRIPTION
				"Hard disk temperature (in Celsius)."
			::= { hardDiskDescriptionEntry 20 }		
	
		hardDiskSASAddr1 OBJECT-TYPE	
			SYNTAX DisplayString 
			MAX-ACCESS read-only
			STATUS current
			DESCRIPTION
				"Hard disk SAS address 1."
			::= { hardDiskDescriptionEntry 21 }
	
		hardDiskSASAddr2 OBJECT-TYPE	
			SYNTAX DisplayString 
			MAX-ACCESS read-only
			STATUS current
			DESCRIPTION
				"Hard disk SAS address 2."
			::= { hardDiskDescriptionEntry 22 }	
	
		hardDiskPrefailState OBJECT-TYPE	
			SYNTAX INTEGER 
				{
				no(1),
				yes(2),
				unknown(255)
				}
			MAX-ACCESS read-only
			STATUS current
			DESCRIPTION
				"Hard disk prefail state."
			::= { hardDiskDescriptionEntry 23 }	
	
		hardDiskHotSpareState OBJECT-TYPE	
			SYNTAX INTEGER 
				{
				none(1),
				global(2),
				dedicated(3),
				commissioned(4),
				emergency(5),
				unknown(255)
				}
			MAX-ACCESS read-write
			STATUS current
			DESCRIPTION
				"Hard disk hot spare state.
				1: None
				   Cancel the global/dedicated hot spare setting, can be set when hardDiskHotSpareState is Global/Dedicated.
				2: Global
				   Can be set only when hardDiskFwState = Unconfigured Good.
				3: Dedicated
				   Can be set only when hardDiskFwState = Unconfigured Good.
				   
				   Setting value described as following:
				   Byte1 - Indicating the hard disk used as dedicated hot spare, fixed to 3.
				   Byte2 - The logical drive index which the hard disk spared for, started from 1.
				   				   
				   For example:
				   Set this hard disk as dedicated hot spare for logical drive 2, the setting value should be
				   0x0203 = 2 * 256 + 3 = 515.
				4: Commissioned (read only)
				5: Emergency (read only)
				255: Unknown (read only)"
			::= { hardDiskDescriptionEntry 24 }		
	
		hardDiskRemnantWearout OBJECT-TYPE	
			SYNTAX INTEGER 
				{
				unknown(255)
				}
			MAX-ACCESS read-only
			STATUS current
			DESCRIPTION
				"Hard disk remnant wearout (100% - 0). Only valid for SSD."
			::= { hardDiskDescriptionEntry 25 }
			
		hardDiskMediaErrCount OBJECT-TYPE	
			SYNTAX INTEGER 
				{
				unknown(4294967295)
				}
			MAX-ACCESS read-only
			STATUS current
			DESCRIPTION
				"Hard disk media error count."
			::= { hardDiskDescriptionEntry 26 }			
			
		hardDiskPrefailErrCount OBJECT-TYPE	
			SYNTAX INTEGER 
				{
				unknown(4294967295)
				}
			MAX-ACCESS read-only
			STATUS current
			DESCRIPTION
				"Hard disk prefail error count."
			::= { hardDiskDescriptionEntry 27 }		
	
		hardDiskOtherErrCount OBJECT-TYPE	
			SYNTAX INTEGER 
				{
				unknown(4294967295)
				}
			MAX-ACCESS read-only
			STATUS current
			DESCRIPTION
				"Hard disk other error count."
			::= { hardDiskDescriptionEntry 28 }		
	
		hardDiskLocationState OBJECT-TYPE	
			SYNTAX INTEGER 
				{
				unknown(1),
				off(2),
				on(3)
				}
			MAX-ACCESS read-write
			STATUS current
			DESCRIPTION
				"Hard disk location state.
				1: Unknown (read only)
				2: Off
				3: On"
			::= { hardDiskDescriptionEntry 29 }
			
		hardDiskCapacityInMB OBJECT-TYPE	
			SYNTAX INTEGER 
				{
				unknown(4294967295)
				}
			MAX-ACCESS read-only
			STATUS current
			DESCRIPTION
				"Hard disk capacity (MB)."
			::= { hardDiskDescriptionEntry 30 } 		
	
--    ****** fru Product information Location *******************************
		fruInfo OBJECT IDENTIFIER ::= { hwiBMC 19 }    

		fruDescriptionTable OBJECT-TYPE
			SYNTAX SEQUENCE OF FruDescriptionEntry 
			MAX-ACCESS not-accessible
			STATUS current
			DESCRIPTION
				"A table containing the FRU information."
			::= { fruInfo 50 }
        
                fruDescriptionEntry OBJECT-TYPE
			SYNTAX FruDescriptionEntry 
			MAX-ACCESS not-accessible
			STATUS current
			DESCRIPTION
				"Information about FRU information."
			INDEX { fruId }
			::= { fruDescriptionTable 1 }
		
		FruDescriptionEntry ::=
			SEQUENCE {
				fruId
					INTEGER, 
				fruBoardManufacturer
					DisplayString,
				fruBoardProductName 
					DisplayString,
				fruBoardSerialNumber  
					DisplayString,
				fruBoardPartNumber  
					DisplayString, 
				fruBoardMfgDate    
					DisplayString,
				fruBoardFileID
					DisplayString, 
				fruProductManufacturer    
					DisplayString, 
				fruProductName    
					DisplayString, 					
				fruProductSerialNumber    
					DisplayString,					
				fruProductPartNumber    
					DisplayString,					
				fruProductVersion
					DisplayString,
				fruProductAssetTag										
					DisplayString,
				fruProductFileID
					DisplayString	
				}
				 

		fruId OBJECT-TYPE	
			SYNTAX INTEGER
			MAX-ACCESS not-accessible
			STATUS current
			DESCRIPTION
				"Information about FRU id."
			::= { fruDescriptionEntry 1 } 
			

		fruBoardManufacturer OBJECT-TYPE
			SYNTAX DisplayString
			MAX-ACCESS read-only
			STATUS current
			DESCRIPTION
				"FRU board manufacturer."
			::= { fruDescriptionEntry 2 }


		fruBoardProductName OBJECT-TYPE
			SYNTAX DisplayString
			MAX-ACCESS read-only
			STATUS current
			DESCRIPTION
				"FRU board product name."
			::= { fruDescriptionEntry 3 }  
 

		fruBoardSerialNumber OBJECT-TYPE
			SYNTAX DisplayString
			MAX-ACCESS read-only
			STATUS current
			DESCRIPTION
				"FRU board serial number."
			::= { fruDescriptionEntry 4 } 			


		fruBoardPartNumber OBJECT-TYPE
			SYNTAX DisplayString
			MAX-ACCESS read-only
			STATUS current
			DESCRIPTION
				"FRU board part number."
			::= { fruDescriptionEntry 5 } 			


		fruBoardMfgDate OBJECT-TYPE
			SYNTAX DisplayString
			MAX-ACCESS read-only
			STATUS current
			DESCRIPTION
				"FRU borad maufacturer date."
			::= { fruDescriptionEntry 6 } 			
 

		fruBoardFileID OBJECT-TYPE
			SYNTAX DisplayString
			MAX-ACCESS read-only
			STATUS current
			DESCRIPTION
				"FRU board file id."
			::= { fruDescriptionEntry 7 }  			


		fruProductManufacturer OBJECT-TYPE
			SYNTAX DisplayString
			MAX-ACCESS read-only
			STATUS current
			DESCRIPTION
				"FRU product maufacturer."
			::= { fruDescriptionEntry 8 } 


		fruProductName OBJECT-TYPE
			SYNTAX DisplayString
			MAX-ACCESS read-only
			STATUS current
			DESCRIPTION
				"FRU product name."
			::= { fruDescriptionEntry 9 } 


		fruProductSerialNumber OBJECT-TYPE
			SYNTAX DisplayString
			MAX-ACCESS read-only
			STATUS current
			DESCRIPTION
				"FRU product serial number."
			::= { fruDescriptionEntry 10 } 
			

		fruProductPartNumber OBJECT-TYPE
			SYNTAX DisplayString
			MAX-ACCESS read-only
			STATUS current
			DESCRIPTION
				"FRU product part number ."
			::= { fruDescriptionEntry 11 } 
			

		fruProductVersion OBJECT-TYPE
			SYNTAX DisplayString
			MAX-ACCESS read-only
			STATUS current
			DESCRIPTION
				"FRU product version."
			::= { fruDescriptionEntry 12 } 


		fruProductAssetTag OBJECT-TYPE
			SYNTAX DisplayString
			MAX-ACCESS read-only
			STATUS current
			DESCRIPTION
				"FRU product asset tag."
			::= { fruDescriptionEntry 13 } 


		fruProductFileID OBJECT-TYPE
			SYNTAX DisplayString
			MAX-ACCESS read-only
			STATUS current
			DESCRIPTION
				"FRU product file id."
			::= { fruDescriptionEntry 14 } 


		fruExtendedELabelDescriptionTable OBJECT-TYPE
			SYNTAX SEQUENCE OF FruExtendedELabelDescriptionEntry 
			MAX-ACCESS not-accessible
			STATUS current
			DESCRIPTION
				"A table containing the FRU extend E-label."
			::= { fruInfo 60 }
        
               fruExtendedELabelDescriptionEntry OBJECT-TYPE
			SYNTAX FruExtendedELabelDescriptionEntry 
			MAX-ACCESS not-accessible
			STATUS current
			DESCRIPTION
				"Information about label."
			INDEX { fruid,fruExtendedELabelIndex }
			::= { fruExtendedELabelDescriptionTable 1 }
		
		FruExtendedELabelDescriptionEntry ::=
			SEQUENCE {
			    fruid
			        INTEGER,
				fruExtendedELabelIndex
					INTEGER, 
				fruExtendedELabelInfo
					DisplayString
				} 
	

		fruid OBJECT-TYPE
			SYNTAX INTEGER
			MAX-ACCESS not-accessible
			STATUS current
			DESCRIPTION
				"Extened fru ID."
			::= { fruExtendedELabelDescriptionEntry 1 }
			
						

		fruExtendedELabelIndex OBJECT-TYPE
			SYNTAX INTEGER
			MAX-ACCESS read-only
			STATUS current
			DESCRIPTION
				"Fru extend E-label index."
			::= { fruExtendedELabelDescriptionEntry 2 } 


		fruExtendedELabelInfo OBJECT-TYPE
			SYNTAX DisplayString
			MAX-ACCESS read-only
			STATUS current
			DESCRIPTION
				"format: key=value"
			::= { fruExtendedELabelDescriptionEntry 3 } 


--    ****** powerStatistic Information *******************************
  
		powerStatistic OBJECT IDENTIFIER ::= { hwiBMC 20 }
			

		peakPower OBJECT-TYPE
			SYNTAX DisplayString
			MAX-ACCESS read-only
			STATUS current
			DESCRIPTION
				"System peak power, unit is W."
			::= { powerStatistic 1 }
			

		peakPowerOccurTime OBJECT-TYPE
			SYNTAX DisplayString
			MAX-ACCESS read-only
			STATUS current
			DESCRIPTION
				"System peak power occur time, based on UTC"
			::= { powerStatistic 2 } 
			

		averagePower OBJECT-TYPE
			SYNTAX DisplayString
			MAX-ACCESS read-only
			STATUS current
			DESCRIPTION
				"System average power, unit is W."
			::= { powerStatistic 3 }
		

		powerConsumption OBJECT-TYPE
			SYNTAX DisplayString
			MAX-ACCESS read-only
			STATUS current
			DESCRIPTION
				"Power consume from power statistic start time, unit is kWh."
			::= { powerStatistic 4 }
		

		powerStatisticStartTime OBJECT-TYPE
			SYNTAX DisplayString
			MAX-ACCESS read-only
			STATUS current
			DESCRIPTION
				"The start time of power statistic, based on UTC.
				the value such as (yyyy-mm-dd hh:mm:ss)."
			::= { powerStatistic 5 }
		

		clearPowerStatistic OBJECT-TYPE
			SYNTAX INTEGER
			        {
			        clearall(1)
			        }			   
			MAX-ACCESS read-write
			STATUS current
			DESCRIPTION
				"clear all power statistic, write only."
			::= { powerStatistic 6 }
			                                                              
			                                                              
--    ****** powerManagement Information *******************************
  
		powerManagement OBJECT IDENTIFIER ::= { hwiBMC 23 }           
			

		powerCappingEnable OBJECT-TYPE
			SYNTAX INTEGER
				{
				disable(1),
				enable(2)
				}
			MAX-ACCESS read-write
			STATUS current
			DESCRIPTION
				"Power capping status. disable 1, enable 2.
				Default value is disable(1)."
			::= { powerManagement 1 }
			

		powerCappingValue OBJECT-TYPE
			SYNTAX INTEGER
			MAX-ACCESS read-write
			STATUS current
			DESCRIPTION
				"Power capping value, the vaule is in [1, 9999]."
			::= { powerManagement 2 } 
			

		powerCappingFailureAction OBJECT-TYPE
			SYNTAX INTEGER           
				{
				eventlog(1),				                               
				eventlogAndPowerOff(2)				
				}
			MAX-ACCESS read-write
			STATUS current
			DESCRIPTION
				"When power capping failed, host system action.
				Default value is eventlog(1)."
			::= { powerManagement 3 }


		pCIeDeviceProperty OBJECT IDENTIFIER ::= { hwiBMC 24 } 
 
 		pCIeDeviceEntireStatus OBJECT-TYPE
			SYNTAX INTEGER 
				{
				ok(1),
				minor(2),
				major(3),
				critical(4),
				absence(5),
				unknown(6)
				}
			MAX-ACCESS read-only
			STATUS current
			DESCRIPTION
				"Information about all standard PCIe device health status."
			::= { pCIeDeviceProperty 1 }
 
		pCIeDeviceDescriptionTable OBJECT-TYPE
			SYNTAX SEQUENCE OF PCIeDeviceDescriptionEntry 
			MAX-ACCESS not-accessible
			STATUS current
			DESCRIPTION
				"A table containing the standard PCIe device."
			::= { pCIeDeviceProperty 50 }
        
                pCIeDeviceDescriptionEntry OBJECT-TYPE
			SYNTAX PCIeDeviceDescriptionEntry 
			MAX-ACCESS not-accessible
			STATUS current
			DESCRIPTION
				"Information about PCIe device."
			INDEX { pCIeDeviceIndex }
			::= { pCIeDeviceDescriptionTable 1 }
		
		PCIeDeviceDescriptionEntry ::=
			SEQUENCE {
				pCIeDeviceIndex
					INTEGER, 
				pCIeDevicePresence
					INTEGER,
				pCIeDeviceStatus
					INTEGER,
				pCIeAvailability
				    INTEGER,
				pCIeDeviceLocation
				    DisplayString,
				pCIeDeviceFunction
				    DisplayString,
				pCIeDeviceDevicename
				    DisplayString,
				pCIeDeviceVID
				    INTEGER,
				pCIeDeviceDID
				    INTEGER,
				pCIeDeviceManufacturer
				    DisplayString,
				pCIeDeviceDescription
				    DisplayString
				}
				 
		
		pCIeDeviceIndex OBJECT-TYPE	
			SYNTAX INTEGER
			MAX-ACCESS not-accessible
			STATUS current
			DESCRIPTION
				"Information about PCIe device index."
			::= { pCIeDeviceDescriptionEntry 1 } 
					
		
		pCIeDevicePresence OBJECT-TYPE
			SYNTAX INTEGER
				{
				absence(1),
				presence(2),
				unknown(3)
				}
			MAX-ACCESS read-only
			STATUS current
			DESCRIPTION
				"Information about PCIe device presence."
			::= { pCIeDeviceDescriptionEntry 2 }

		
		pCIeDeviceStatus OBJECT-TYPE
			SYNTAX INTEGER 
				{
				ok(1),
				minor(2),
				major(3),
				critical(4),
				absence(5),
				unknown(6)
				}
			MAX-ACCESS read-only
			STATUS current
			DESCRIPTION
				"Information about PCIe device health."
			::= { pCIeDeviceDescriptionEntry 3 }  
			
			   
         pCIeAvailability OBJECT-TYPE
            SYNTAX INTEGER 
                 {
                 unknown(1),
                 disabled(2),
                 backup(3),
                 active(4)
                 }
            MAX-ACCESS read-only
            STATUS current
            DESCRIPTION
            "Information about PCIe device availability."
            ::= { pCIeDeviceDescriptionEntry 4 }
					
		pCIeDeviceLocation OBJECT-TYPE
			SYNTAX DisplayString
			MAX-ACCESS read-only
			STATUS current
			DESCRIPTION
				" PCIe physical location."
			::= { pCIeDeviceDescriptionEntry 5 }

		
		pCIeDeviceFunction OBJECT-TYPE
			SYNTAX DisplayString
			MAX-ACCESS read-only
			STATUS current
			DESCRIPTION
				" PCIe logic function."
			::= { pCIeDeviceDescriptionEntry 6 }  
 
		
		pCIeDeviceDevicename OBJECT-TYPE
			SYNTAX DisplayString
			MAX-ACCESS read-only
			STATUS current
			DESCRIPTION
				" PCIe devicename."
			::= { pCIeDeviceDescriptionEntry 7 } 

		pCIeDeviceVID OBJECT-TYPE	
			SYNTAX INTEGER
			MAX-ACCESS read-only
			STATUS current
			DESCRIPTION
				"PCIe device VID."
			::= { pCIeDeviceDescriptionEntry 8 } 
			
		pCIeDeviceDID OBJECT-TYPE	
			SYNTAX INTEGER
			MAX-ACCESS read-only
			STATUS current
			DESCRIPTION
				"PCIe device DID."
			::= { pCIeDeviceDescriptionEntry 9 } 
			
		pCIeDeviceManufacturer OBJECT-TYPE
			SYNTAX DisplayString
			MAX-ACCESS read-only
			STATUS current
			DESCRIPTION
				" PCIe device manufacturer."
			::= { pCIeDeviceDescriptionEntry 10 }  
			
		pCIeDeviceDescription OBJECT-TYPE
			SYNTAX DisplayString
			MAX-ACCESS read-only
			STATUS current
			DESCRIPTION
				" PCIe device description."
			::= { pCIeDeviceDescriptionEntry 11 } 
			                        

		mezzProperty OBJECT IDENTIFIER ::= { hwiBMC 25 }    

		mezzDescriptionTable OBJECT-TYPE
			SYNTAX SEQUENCE OF MezzDescriptionEntry 
			MAX-ACCESS not-accessible
			STATUS current
			DESCRIPTION
				"A table containing the mezz information."
			::= { mezzProperty 50 }
        
            mezzDescriptionEntry  OBJECT-TYPE
			SYNTAX MezzDescriptionEntry 
			MAX-ACCESS not-accessible
			STATUS current
			DESCRIPTION
				"Information about mezz information."
			INDEX { mezzCardIndex }
			::= { mezzDescriptionTable 1 }
		
		MezzDescriptionEntry  ::=
			SEQUENCE {
				mezzCardIndex
					INTEGER,
				mezzCardLocation
					DisplayString,
				mezzCardFunction 
					DisplayString,
				mezzCardDevicename
					DisplayString
				}
				 
		
		mezzCardIndex OBJECT-TYPE	
			SYNTAX INTEGER
			MAX-ACCESS not-accessible
			STATUS current
			DESCRIPTION
				" Information about mezz card index."
			::= { mezzDescriptionEntry 1 } 
			
		
		mezzCardLocation OBJECT-TYPE
			SYNTAX DisplayString
			MAX-ACCESS read-only
			STATUS current
			DESCRIPTION
				" Mezz card physical location."
			::= { mezzDescriptionEntry 2 }

		
		mezzCardFunction OBJECT-TYPE
			SYNTAX DisplayString
			MAX-ACCESS read-only
			STATUS current
			DESCRIPTION
				" Mezz card logic function."
			::= { mezzDescriptionEntry 3 }  
 
		
		mezzCardDevicename OBJECT-TYPE
			SYNTAX DisplayString
			MAX-ACCESS read-only
			STATUS current
			DESCRIPTION
				" Mezz card devicename."
			::= { mezzDescriptionEntry 4 }
			
	 temperatureProperty OBJECT IDENTIFIER ::= { hwiBMC 26 } 
	 
	 temperatureDescriptionTable OBJECT-TYPE
			SYNTAX SEQUENCE OF TemperatureDescriptionEntry 
			MAX-ACCESS not-accessible
			STATUS current
			DESCRIPTION
				"A table containing the temperature infomation."
			::= { temperatureProperty 50 }
        
            temperatureDescriptionEntry  OBJECT-TYPE
			SYNTAX TemperatureDescriptionEntry 
			MAX-ACCESS not-accessible
			STATUS current
			DESCRIPTION
				"Information about temperature."
			INDEX { temperatureIndex }
			::= { temperatureDescriptionTable 1 }
		
		TemperatureDescriptionEntry  ::=
			SEQUENCE {
				temperatureIndex
					INTEGER,
				temperatureObject
					DisplayString,
				temperatureReading 
					INTEGER,
				temperatureUpperNonRecoverable
					INTEGER,
				temperatureUpperCritical
					INTEGER,
				temperatureUpperMinor
					INTEGER,
				temperatureLowerNonRecoverable
					INTEGER,
				temperatureLowerCritical
					INTEGER,
				temperatureLowerMinor
					INTEGER
				}
				 
		
		temperatureIndex OBJECT-TYPE	
			SYNTAX INTEGER
			MAX-ACCESS not-accessible
			STATUS current
			DESCRIPTION
				" Information about temperature index."
			::= { temperatureDescriptionEntry 1 } 

		temperatureObject OBJECT-TYPE	
			SYNTAX DisplayString
			MAX-ACCESS read-only
			STATUS current
			DESCRIPTION
				" Information about temperature object."
			::= { temperatureDescriptionEntry 2 }  
			
		temperatureReading OBJECT-TYPE	
			SYNTAX INTEGER
			MAX-ACCESS read-only
			STATUS current
			DESCRIPTION
				" Information about temperature reading,the unit is 1/10 Celsius degree.
				If power off, the CPU temperature cannot be readable and is set to 0."
			::= { temperatureDescriptionEntry 3 }   
			
		temperatureUpperNonRecoverable OBJECT-TYPE	
			SYNTAX INTEGER
			MAX-ACCESS read-only
			STATUS current
			DESCRIPTION
				" Information about temperature upper nonrecoverable threshold,the unit is 1/10 Celsius degree,65535 represent NA."
			::= { temperatureDescriptionEntry 4 }
			
		temperatureUpperCritical OBJECT-TYPE	
			SYNTAX INTEGER
			MAX-ACCESS read-only
			STATUS current
			DESCRIPTION
				" Information about temperature upper critical threshold,the unit is 1/10 Celsius degree,65535 represent NA."
			::= { temperatureDescriptionEntry 5 }

		temperatureUpperMinor OBJECT-TYPE	
			SYNTAX INTEGER
			MAX-ACCESS read-only
			STATUS current
			DESCRIPTION
				" Information about temperature upper minor threshold,the unit is 1/10 Celsius degree,65535 represent NA."
			::= { temperatureDescriptionEntry 6 }
			
		temperatureLowerNonRecoverable OBJECT-TYPE	
			SYNTAX INTEGER
			MAX-ACCESS read-only
			STATUS current
			DESCRIPTION
				" Information about temperature lower nonrecoverable threshold,the unit is 1/10 Celsius degree,65535 represent NA."
			::= { temperatureDescriptionEntry 7 }
			
		temperatureLowerCritical OBJECT-TYPE	
			SYNTAX INTEGER
			MAX-ACCESS read-only
			STATUS current
			DESCRIPTION
				" Information about temperature lower critical threshold,the unit is 1/10 Celsius degree,65535 represent NA."
			::= { temperatureDescriptionEntry 8 }
			
		temperatureLowerMinor OBJECT-TYPE	
			SYNTAX INTEGER
			MAX-ACCESS read-only
			STATUS current
			DESCRIPTION
				" Information about temperature lower minor threshold,the unit is 1/10 Celsius degree,65535 represent NA."
			::= { temperatureDescriptionEntry 9 }        
			
--  ****************** networkTimeProtocol information **********************		
		networkTimeProtocol OBJECT IDENTIFIER ::= { hwiBMC 27 }    

		ntpSupport OBJECT-TYPE	
			SYNTAX INTEGER
			{
				nosupport (1),
				support (2)				
			}			
			MAX-ACCESS read-only
			STATUS current
			DESCRIPTION
				"Information about whether the system support NTP.If the system does not support NTP,then we can ignore the value returned by working the nodes of networkTimeProtocol."
			::= { networkTimeProtocol 1 } 
		
		ntpEnabled OBJECT-TYPE	
			SYNTAX INTEGER
			{
				disable (1),
				enable (2)				
			}			
			MAX-ACCESS read-write
			STATUS current
			DESCRIPTION
				"Enable or disable NTP."
			::= { networkTimeProtocol 2 } 
			
		preferredNTPServer OBJECT-TYPE
			SYNTAX DisplayString
			MAX-ACCESS read-write
			STATUS current
			DESCRIPTION
				"Preferred NTP server IPv4 or IPv6 address.
                This value is right IP address or empty, 
                the default value is empty."
			::= { networkTimeProtocol 3 }
			
		alternateNTPServer OBJECT-TYPE
			SYNTAX DisplayString
			MAX-ACCESS read-write
			STATUS current
			DESCRIPTION
				"Alternate DNS server IPv4 or IPv6 address.
                This value is right IP address or empty, 
                the default value is empty."
			::= { networkTimeProtocol 4 }
			

		ntpServersource OBJECT-TYPE
			SYNTAX INTEGER
				{
				manual (1),
				auto (2)
				}
			MAX-ACCESS read-write
			STATUS current
			DESCRIPTION
				"Information about NTP source."
			::= { networkTimeProtocol 5 }						

		bindNTPIPProtocol OBJECT-TYPE
			SYNTAX INTEGER
				{
				ipv4 (1),
				ipv6 (2)
				}
			MAX-ACCESS read-write
			STATUS current
			DESCRIPTION
				"Information about NTP bind ip protocol."
			::= { networkTimeProtocol 6 }                                           
		
		ntpAuthEnabled OBJECT-TYPE	
			SYNTAX INTEGER
			{
				disable (1),
				enable (2)				
			}			
			MAX-ACCESS read-write
			STATUS current
			DESCRIPTION
				"Enable or disable NTP authentication."
			::= { networkTimeProtocol 7 }
			          
		ntpImportGroupkey OBJECT-TYPE	
			SYNTAX DisplayString			
			MAX-ACCESS read-write
			STATUS current
			DESCRIPTION 
			"Import group key." 
			::= { networkTimeProtocol 8 }
			
		ntpGroupkeyState OBJECT-TYPE
			SYNTAX INTEGER
				{
				notimported (1),
				imported (2)
				}
			MAX-ACCESS read-only
			STATUS current
			DESCRIPTION
				"Information about NTP Group key."
			::= { networkTimeProtocol 9 }
			
	snmpMIBConfig OBJECT IDENTIFIER ::= { hwiBMC 29 }  
			
		snmpV3Algorithm OBJECT-TYPE	
			SYNTAX INTEGER
			{
             mD5andDES (1),
             mD5andAES (2),
             sHA1andDES (3),
             sHA1andAES (4)				
			}			
			MAX-ACCESS read-write
			STATUS current
			DESCRIPTION
				"Information about the authentication and encryption algorithm for SNMP V3.
				the format is AUTHORITYandENCRPTION: 
                MD5andDES(1),
                MD5andAES(2),
                SHA1andDES(3),
                SHA1andAES(4).                
                NOTE: the snmp will restart after this value changed.
                "
			::= { snmpMIBConfig 1 }	

	firmwareUpgrade OBJECT IDENTIFIER ::= { hwiBMC 30 }
	
	firmwareUpgradeStart OBJECT-TYPE
			SYNTAX DisplayString
			MAX-ACCESS read-write
			STATUS current
			DESCRIPTION
				"Start upgrade firmware,
				The set format is: <firmware URI>,[effect mode], with max length 256.
				The <firmware URI> format is: /PATH/FILE.   
				The [effect mode] is an optional parameter. It only refers to upgrading iBMC firmware. The definition is as following and default is 2.  
				1: manually reboot later;
				2: auto reboot after upgrade;
				In addition, This parameter is ignored in iBMC which is 2.36 and above.
				
				e.g.: /tmp/image.hpm,1.
				
				NOTE:
				1.Do not power off the server or restart the iBMC during the firmware upgrade.   
                2.If the firmware fails to upgrade, check whether the iBMC's memory capacity is sufficient and the upgrade file is correct.   
                3.Upgrade BIOS firmware, system needs two minutes of preparation time.   
                4.Do not shut down or restart the OS during a BIOS upgrade."
			::= { firmwareUpgrade 1 } 
		
	firmwareUpgradeState OBJECT-TYPE
			SYNTAX INTEGER
			MAX-ACCESS read-only
			STATUS current
			DESCRIPTION
				"Information about firmware upgrading state.
				the value defined as:
				  -1: upgrade not start or completed,
                  -2: file uploading,
                  -3: checking preUpgrade,
                  -4: invalid URI or file not exist,
                  -5: file upload failed,
                  -6: file too large or memory not enough,
                  -7: invalid upgrade package,
                  -8: not support upgrade in current state,
                  -9: upgrade failed,
                  [0,100]:represents upgrade progress in percentage while firmware being upgrading."
			::= { firmwareUpgrade 2 } 
			
	firmwareUpgradeDetailedResults OBJECT-TYPE
		SYNTAX DisplayString
		MAX-ACCESS read-only
		STATUS current
		DESCRIPTION
			"Detailed results about firmware upgrade."
		::= { firmwareUpgrade 3 } 
			
--    ******* currentCertInfo Information *******************************
	certificate OBJECT IDENTIFIER ::= { hwiBMC 31 }    
	
	currentCertInfo OBJECT IDENTIFIER ::= { certificate 1 }
	  
	ownerCountry OBJECT-TYPE
			SYNTAX DisplayString
			MAX-ACCESS read-only
			STATUS current
			DESCRIPTION 
			"Owner country of current certificate, with length of 2." 
			::= { currentCertInfo 1 } 		
	
	ownerState OBJECT-TYPE
			SYNTAX DisplayString
			MAX-ACCESS read-only
			STATUS current
			DESCRIPTION 
			"Owner state of current certificate, with length of [0,64]." 
			::= { currentCertInfo 2 }   
	
	ownerLocation OBJECT-TYPE
			SYNTAX DisplayString
			MAX-ACCESS read-only
			STATUS current
			DESCRIPTION 
			"Owner location of current certificate, with length of [0,64]." 
			::= { currentCertInfo 3 } 		
	
	ownerOrganization OBJECT-TYPE
			SYNTAX DisplayString
			MAX-ACCESS read-only
			STATUS current
			DESCRIPTION 
			"Owner organization of current certificate, with length of [0,64]." 
			::= { currentCertInfo 4 }  
			
	ownerOrganizationUnit OBJECT-TYPE
			SYNTAX DisplayString
			MAX-ACCESS read-only
			STATUS current
			DESCRIPTION 
			"Owner organization unit of current certificate, with length of [0,64]." 
			::= { currentCertInfo 5 }

	ownerCommonName OBJECT-TYPE
			SYNTAX DisplayString
			MAX-ACCESS read-only
			STATUS current
			DESCRIPTION 
			"Owner common name of current certificate, with length of [1,64]." 
			::= { currentCertInfo 6 }
			
			
    issuerCountry OBJECT-TYPE
			SYNTAX DisplayString
			MAX-ACCESS read-only
			STATUS current
			DESCRIPTION 
			"Issuer country of current certificate, with length of 2." 
			::= { currentCertInfo 7 } 		
	
	issuerState OBJECT-TYPE
			SYNTAX DisplayString
			MAX-ACCESS read-only
			STATUS current
			DESCRIPTION 
			"Issuer state of current certificate, with length of [0,64]." 
			::= { currentCertInfo 8 }   
	
	issuerLocation OBJECT-TYPE
			SYNTAX DisplayString
			MAX-ACCESS read-only
			STATUS current
			DESCRIPTION 
			"Issuer location of current certificate, with length of [0,64]." 
			::= { currentCertInfo 9 } 		
	
	issuerOrganization OBJECT-TYPE
			SYNTAX DisplayString
			MAX-ACCESS read-only
			STATUS current
			DESCRIPTION 
			"Issuer organization of current certificate, with length of [0,64]." 
			::= { currentCertInfo 10 }  
			
	issuerOrganizationUnit OBJECT-TYPE
			SYNTAX DisplayString
			MAX-ACCESS read-only
			STATUS current
			DESCRIPTION 
			"Issuer organization unit of current certificate, with length of [0,64]." 
			::= { currentCertInfo 11 }

	issuerCommonName OBJECT-TYPE
			SYNTAX DisplayString
			MAX-ACCESS read-only
			STATUS current
			DESCRIPTION 
			"Issuer common name of current certificate, with length of [1,64]." 
			::= { currentCertInfo 12 }  
	
	
	certStartTime OBJECT-TYPE
			SYNTAX DisplayString
			MAX-ACCESS read-only
			STATUS current
			DESCRIPTION 
			"Start time of current certificate." 
			::= { currentCertInfo 13 }
			
	certExpiration OBJECT-TYPE
			SYNTAX DisplayString
			MAX-ACCESS read-only
			STATUS current
			DESCRIPTION 
			"Expiration of current certificate." 
			::= { currentCertInfo 14 }
	
	
	csrRequestInfo OBJECT IDENTIFIER ::= { certificate 2 } 
	
	reqCountry OBJECT-TYPE
			SYNTAX DisplayString
			MAX-ACCESS read-write
			STATUS current
			DESCRIPTION 
			"Owner country of request certificate, with length of 2, contains any letters." 
			::= { csrRequestInfo 1 } 		
	
	reqState OBJECT-TYPE
			SYNTAX DisplayString
			MAX-ACCESS read-write
			STATUS current
			DESCRIPTION 
			"Owner state of request certificate, with length of [0,64], contains any digits, letters, or the symbol spaces." 
			::= { csrRequestInfo 2 }   
	
	reqLocation OBJECT-TYPE
			SYNTAX DisplayString
			MAX-ACCESS read-write
			STATUS current
			DESCRIPTION 
			"Owner location of request certificate, with length of [0,64], contains any digits, letters, or the symbol spaces." 
			::= { csrRequestInfo 3 } 		
	
	reqOrganization OBJECT-TYPE
			SYNTAX DisplayString
			MAX-ACCESS read-write
			STATUS current
			DESCRIPTION 
			"Owner organization of request certificate, with length of [0,64], contains any digits, letters, or - _ . spaces symbol." 
			::= { csrRequestInfo 4 }  
			
	reqOrganizationUnit OBJECT-TYPE
			SYNTAX DisplayString
			MAX-ACCESS read-write
			STATUS current
			DESCRIPTION 
			"Owner organization unit of request certificate, with length of [0,64], contains any digits, letters, or - _ . spaces symbol." 
			::= { csrRequestInfo 5 }

	reqCommonName OBJECT-TYPE
			SYNTAX DisplayString
			MAX-ACCESS read-write
			STATUS current
			DESCRIPTION 
			"Owner common name of request certificate, with length of [1,64], contains any digits, letters, or - _ . spaces symbol." 
			::= { csrRequestInfo 6 }
			
	csrGenerate OBJECT-TYPE
			SYNTAX INTEGER 		
				{
				csrGenerate(1)			                               				
				}

			MAX-ACCESS read-write
			STATUS current
			DESCRIPTION 
			"Start to generate CSR of request certificate." 
			::= { csrRequestInfo 7 }
			
	csrExport OBJECT-TYPE
			SYNTAX DisplayString
			MAX-ACCESS read-only
			STATUS current
			DESCRIPTION 
			"Acquire the CSR of request certificate. The value is empty if request csr not exist." 
			::= { csrRequestInfo 8 }
			
	certificateImport OBJECT-TYPE
			SYNTAX DisplayString			
			MAX-ACCESS read-write
			STATUS current
			DESCRIPTION 
			"Import server certificate." 
			::= { csrRequestInfo 9 }

	csrStatus OBJECT-TYPE
			SYNTAX INTEGER
				{
				notStartedOrHasSuccessfullyCompleted (1),
				beingGenerated (2),
				failsGenerated (3)
				}
			MAX-ACCESS read-only
			STATUS current
			DESCRIPTION
				"The status of generating CSR.
				CSR generation has not started or has successfully completed(1)
				A CSR is being generated (2)
				A CSR fails to be generated (3)."
			::= { csrRequestInfo 10 }  			
			
	customCertInsert OBJECT IDENTIFIER ::= { certificate 3 }
	
	customCertificateContent OBJECT-TYPE
			SYNTAX DisplayString
			MAX-ACCESS read-write
			STATUS current
			DESCRIPTION 
			"Set custom certificate content." 
			::= { customCertInsert 1 }
			
	customCertificatePasswd OBJECT-TYPE
			SYNTAX DisplayString
			MAX-ACCESS read-write
			STATUS current
			DESCRIPTION 
			"Set custom certificate password, with max len 127." 
			::= { customCertInsert 2 }
			
	customCertificateImport OBJECT-TYPE
			SYNTAX INTEGER 
			    {
			    customCertificateImport(1)			
			    }
			MAX-ACCESS read-write
			STATUS current
			DESCRIPTION 
			"The action of import custom certificate." 
			::= { customCertInsert 3 }
                                               
	caCertInfoTable OBJECT-TYPE
		SYNTAX SEQUENCE OF CACertInfoEntry 
		MAX-ACCESS read-only
		STATUS current
		DESCRIPTION
			"A table containing the list of certificate information."
		::= { certificate 4 }
	
			caCertInfoEntry OBJECT-TYPE
		SYNTAX CACertInfoEntry
		MAX-ACCESS read-only
		STATUS current
		DESCRIPTION
			"Information about certificate."
		INDEX { certIndex }
		::= { caCertInfoTable 1 }	
		
		CACertInfoEntry ::=
			SEQUENCE {
			caCertIndex
				INTEGER, 
			caCertType
				DisplayString,
			caCertOwnerCountry
				DisplayString,
			caCertOwnerState 
				DisplayString, 	
			caCertOwnerLocation 
				DisplayString,
			caCertOwnerOrganization
				DisplayString,
			caCertOwnerOrganizationUnit 
				DisplayString,
			caCertOwnerCommonName 
				DisplayString, 
			caCertIssuerCountry 
				DisplayString, 
			caCertIssuerState 
				DisplayString, 					
			caCertIssuerLocation 
				DisplayString,
			caCertIssuerOrganization 
				DisplayString,
			caCertIssuerOrganizationUnit
				DisplayString,
			caCertIssuerCommonName 
				DisplayString,
			caCertStartTime
				DisplayString,
			caCertExpiration
				DisplayString,
			caCertSN
				DisplayString 
				}
				
		caCertIndex OBJECT-TYPE	
			SYNTAX INTEGER
			MAX-ACCESS read-only
			STATUS current
			DESCRIPTION
				"Information about certificate index."
			::= { caCertInfoEntry 1 } 
			
		caCertType OBJECT-TYPE
			SYNTAX DisplayString
			MAX-ACCESS read-only
			STATUS current
			DESCRIPTION 
			"Information about certificate type." 
			::= { caCertInfoEntry 2 } 	
	
		caCertOwnerCountry OBJECT-TYPE
			SYNTAX DisplayString
			MAX-ACCESS read-only
			STATUS current
			DESCRIPTION 
			"Owner country of current certificate, with length of 2." 
			::= { caCertInfoEntry 3 } 		
		
		caCertOwnerState OBJECT-TYPE
			SYNTAX DisplayString
			MAX-ACCESS read-only
			STATUS current
			DESCRIPTION 
			"Owner state of current certificate, with length of [0,64]." 
			::= { caCertInfoEntry 4 }   
	
		caCertOwnerLocation OBJECT-TYPE
			SYNTAX DisplayString
			MAX-ACCESS read-only
			STATUS current
			DESCRIPTION 
			"Owner location of current certificate, with length of [0,64]." 
			::= { caCertInfoEntry 5 } 		
		
		caCertOwnerOrganization OBJECT-TYPE
			SYNTAX DisplayString
			MAX-ACCESS read-only
			STATUS current
			DESCRIPTION 
			"Owner organization of current certificate, with length of [0,64]." 
			::= { caCertInfoEntry 6 }  
				
		caCertOwnerOrganizationUnit OBJECT-TYPE
			SYNTAX DisplayString
			MAX-ACCESS read-only
			STATUS current
			DESCRIPTION 
			"Owner organization unit of current certificate, with length of [0,64]." 
			::= { caCertInfoEntry 7 }

		caCertOwnerCommonName OBJECT-TYPE
			SYNTAX DisplayString
			MAX-ACCESS read-only
			STATUS current
			DESCRIPTION 
			"Owner common name of current certificate, with length of [1,64]." 
			::= { caCertInfoEntry 8 }
			
				
		caCertIssuerCountry OBJECT-TYPE
			SYNTAX DisplayString
			MAX-ACCESS read-only
			STATUS current
			DESCRIPTION 
			"Issuer country of current certificate, with length of 2." 
			::= { caCertInfoEntry 9 } 		
		
		caCertIssuerState OBJECT-TYPE
			SYNTAX DisplayString
			MAX-ACCESS read-only
			STATUS current
			DESCRIPTION 
			"Issuer state of current certificate, with length of [0,64]." 
			::= { caCertInfoEntry 10 }   
		
		caCertIssuerLocation OBJECT-TYPE
			SYNTAX DisplayString
			MAX-ACCESS read-only
			STATUS current
			DESCRIPTION 
			"Issuer location of current certificate, with length of [0,64]." 
			::= { caCertInfoEntry 11 } 		
		
		caCertIssuerOrganization OBJECT-TYPE
			SYNTAX DisplayString
			MAX-ACCESS read-only
			STATUS current
			DESCRIPTION 
			"Issuer organization of current certificate, with length of [0,64]." 
			::= { caCertInfoEntry 12 }  
				
		caCertIssuerOrganizationUnit OBJECT-TYPE
			SYNTAX DisplayString
			MAX-ACCESS read-only
			STATUS current
			DESCRIPTION 
			"Issuer organization unit of current certificate, with length of [0,64]." 
			::= { caCertInfoEntry 13 }

		caCertIssuerCommonName OBJECT-TYPE
			SYNTAX DisplayString
			MAX-ACCESS read-only
			STATUS current
			DESCRIPTION 
			"Issuer common name of current certificate, with length of [1,64]." 
			::= { caCertInfoEntry 14 }  
		
		
		caCertStartTime OBJECT-TYPE
			SYNTAX DisplayString
			MAX-ACCESS read-only
			STATUS current
			DESCRIPTION 
			"Start time of current certificate." 
			::= { caCertInfoEntry 15 }
				
		caCertExpiration OBJECT-TYPE
			SYNTAX DisplayString
			MAX-ACCESS read-only
			STATUS current
			DESCRIPTION 
			"Expiration of current certificate." 
			::= { caCertInfoEntry 16 }
				
		caCertSN OBJECT-TYPE
			SYNTAX DisplayString
			MAX-ACCESS read-only
			STATUS current
			DESCRIPTION 
			"Serial Number of current certificate." 
			::= { caCertInfoEntry 17 }
			
	hwTrap OBJECT IDENTIFIER ::= { hwiBMC 500 } 
	
	hwTrapVar OBJECT IDENTIFIER ::= { hwTrap 1 }

		hwTrapSeq OBJECT-TYPE
			SYNTAX INTEGER
			MAX-ACCESS read-only
			STATUS current
			DESCRIPTION
				"Trap sequence"
			::= { hwTrapVar 1 }
			
		hwTrapSensorName OBJECT-TYPE
			SYNTAX DisplayString
			MAX-ACCESS read-only
			STATUS current
			DESCRIPTION
				"Trap sensor name"
			::= { hwTrapVar 2 }   
			
		hwTrapEvent OBJECT-TYPE
			SYNTAX DisplayString
			MAX-ACCESS read-only
			STATUS current
			DESCRIPTION
				"Trap description "
			::= { hwTrapVar 3 }
			
		hwTrapSeverity OBJECT-TYPE
			SYNTAX INTEGER
			        {
				ok(1),
				minor(2),
				major(3),
				critical(4)
				}
			MAX-ACCESS read-only
			STATUS current
			DESCRIPTION
				"Trap severity
				1  - ok,
				2  - minor,
				3  - major,
				4  - critical."
			::= { hwTrapVar 4 }
			
		hwTrapEventCode OBJECT-TYPE
			SYNTAX DisplayString
			MAX-ACCESS read-only
			STATUS current
			DESCRIPTION
				"Trap EventCode"
			::= { hwTrapVar 5 } 
			
	    hwTrapEventData2 OBJECT-TYPE
			SYNTAX INTEGER
			MAX-ACCESS read-only
			STATUS current
			DESCRIPTION
				"Trap Event Data 2"
			::= { hwTrapVar 6 }
			
		hwTrapEventData3 OBJECT-TYPE
			SYNTAX INTEGER
			MAX-ACCESS read-only
			STATUS current
			DESCRIPTION
				"Trap Event Data 3"
			::= { hwTrapVar 7 } 
			
		hwTrapServerIdentity OBJECT-TYPE
			SYNTAX DisplayString
			MAX-ACCESS read-only
			STATUS current
			DESCRIPTION
				"Trap Sever Identity"
			::= { hwTrapVar 8 }
			
		hwTrapLocation OBJECT-TYPE
			SYNTAX DisplayString
			MAX-ACCESS read-only
			STATUS current
			DESCRIPTION
				"Trap location"
			::= { hwTrapVar 9 }

		hwTrapTime OBJECT-TYPE
			SYNTAX DisplayString
			MAX-ACCESS read-only
			STATUS current
			DESCRIPTION
				"Trap time"
			::= { hwTrapVar 10 }
	
	hwServerTRAPObject OBJECT IDENTIFIER ::= { hwTrap 10 }

	
    hwOEM OBJECT IDENTIFIER ::= {hwServerTRAPObject 1} 
    
    hwOEMEvent NOTIFICATION-TYPE
      OBJECTS { hwTrapSeq, hwTrapEvent,hwTrapSeverity,hwTrapServerIdentity, hwTrapLocation, hwTrapTime } 
      STATUS  current
      DESCRIPTION
              "Huawei OEM event"
      ::= { hwOEM 1 }

    hwPhysicalSecurity OBJECT IDENTIFIER ::= {hwServerTRAPObject 5} 
    
    hwChassisIntrusion NOTIFICATION-TYPE
      OBJECTS { hwTrapSeq, hwTrapSensorName, hwTrapEvent, hwTrapSeverity, hwTrapEventCode, hwTrapServerIdentity, hwTrapLocation, hwTrapTime } 
      STATUS  current
      DESCRIPTION
              "General Chassis Intrusion"
      ::= { hwPhysicalSecurity 1 }
	
    hwCPU OBJECT IDENTIFIER ::= {hwServerTRAPObject 7} 
    
    hwCPUCATError NOTIFICATION-TYPE
      OBJECTS { hwTrapSeq, hwTrapSensorName, hwTrapEvent, hwTrapSeverity, hwTrapEventCode, hwTrapServerIdentity, hwTrapLocation, hwTrapTime }
      STATUS  current
      DESCRIPTION
              "CPU CAT error"
      ::= { hwCPU 1 }

    hwCPUCATErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU CAT error deassert"
      ::= { hwCPU 2 }

    hwCPUThermalTrip NOTIFICATION-TYPE
      OBJECTS { hwTrapSeq, hwTrapSensorName, hwTrapEvent, hwTrapSeverity, hwTrapEventCode, hwTrapServerIdentity, hwTrapLocation, hwTrapTime }
      STATUS  current
      DESCRIPTION
              "CPU thermal trip"
      ::= { hwCPU 17 }

    hwCPUThermalTripDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU thermal trip deassert"
      ::= { hwCPU 18 }

    hwCPUSelfTestFail NOTIFICATION-TYPE
      OBJECTS { hwTrapSeq, hwTrapSensorName, hwTrapEvent, hwTrapSeverity, hwTrapEventCode, hwTrapServerIdentity, hwTrapLocation, hwTrapTime }
      STATUS  current
      DESCRIPTION
              "CPU FRB1/BIST failure"
      ::= { hwCPU 33 }

    hwCPUSelfTestFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU FRB1/BIST failure deassert"
      ::= { hwCPU 34 }


    hwCPUCfgError NOTIFICATION-TYPE
      OBJECTS { hwTrapSeq, hwTrapSensorName, hwTrapEvent, hwTrapSeverity, hwTrapEventCode, hwTrapServerIdentity, hwTrapLocation, hwTrapTime }
      STATUS  current
      DESCRIPTION
              "CPU configure error"
      ::= { hwCPU 81 }

    hwCPUCfgErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU configure error deassert"
      ::= { hwCPU 82 }

    hwCPUPresence NOTIFICATION-TYPE
      OBJECTS { hwTrapSeq, hwTrapSensorName, hwTrapEvent, hwTrapSeverity, hwTrapEventCode, hwTrapServerIdentity, hwTrapLocation, hwTrapTime }
      STATUS  current
      DESCRIPTION
              "CPU Presence"
      ::= { hwCPU 113 }

    hwCPUPresenceDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU Presence deassert"
      ::= { hwCPU 114 }

    hwCPUOffline NOTIFICATION-TYPE
      OBJECTS { hwTrapSeq, hwTrapSensorName, hwTrapEvent, hwTrapSeverity, hwTrapEventCode, hwTrapServerIdentity, hwTrapLocation, hwTrapTime }
      STATUS  current
      DESCRIPTION
              "CPU offline"
      ::= { hwCPU 129 }

    hwCPUOfflineDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU offline deassert"
      ::= { hwCPU 130 }

    hwCPUMCE NOTIFICATION-TYPE
      OBJECTS { hwTrapSeq, hwTrapSensorName, hwTrapEvent, hwTrapSeverity, hwTrapEventCode, hwTrapServerIdentity, hwTrapLocation, hwTrapTime }
      STATUS  current
      DESCRIPTION
              "CPU MCE occured"
      ::= { hwCPU 177 }

    hwCPUMCEDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU MCE deassert"
      ::= { hwCPU 178 }  

    hwVMSELinkFail NOTIFICATION-TYPE
      OBJECTS { hwTrapSeq, hwTrapSensorName, hwTrapEvent, hwTrapSeverity, hwTrapEventCode, hwTrapServerIdentity, hwTrapLocation, hwTrapTime }
      STATUS  current
      DESCRIPTION
              "CPU VMSE link failure in mirror mode"
      ::= { hwCPU 193 }

    hwVMSELinkFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU VMSE link failure in mirror mode deassert"
      ::= { hwCPU 194 }

	
    hwPowerSupply OBJECT IDENTIFIER ::= {hwServerTRAPObject 8}
    
    hwPowerSupplyFault NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply Fault"
      ::= { hwPowerSupply 17 }

    hwPowerSupplyFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply Fault Deassert"
      ::= { hwPowerSupply 18 }


    hwPowerSupplyPredictiveFailure NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply Predictive Failure"
      ::= { hwPowerSupply 33 }

    hwPowerSupplyPredictiveFailureDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply Predictive Failure Deassert"
      ::= { hwPowerSupply 34 }

    hwPowerSupplyInputLost NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply input lost"
      ::= { hwPowerSupply 49 }

    hwPowerSupplyInputLostDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Power Supply input lost Deassert"
      ::= { hwPowerSupply 50 }
	  
    hwPowerSupplyACLost NOTIFICATION-TYPE
      OBJECTS { hwTrapSeq, hwTrapSensorName, hwTrapEvent, hwTrapSeverity, hwTrapEventCode, hwTrapServerIdentity, hwTrapLocation, hwTrapTime }
      STATUS  current
      DESCRIPTION
              "AC lost or out-of-range"
      ::= { hwPowerSupply 65 }
	  
    hwPowerSupplyACLostDeassert NOTIFICATION-TYPE
      OBJECTS { hwTrapSeq, hwTrapSensorName, hwTrapEvent, hwTrapSeverity, hwTrapEventCode, hwTrapServerIdentity, hwTrapLocation, hwTrapTime }
      STATUS  current
      DESCRIPTION
              "AC lost or out-of-range Deassert"
      ::= { hwPowerSupply 66 }

    hwMemory OBJECT IDENTIFIER ::= {hwServerTRAPObject 12}
    
    hwCorrectableECC NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory correctable ECC error occurred"
      ::= { hwMemory 1 }

    hwCorrectableECCDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory correctable ECC error deassert"
      ::= { hwMemory 2 }

    hwUncorrectableECC NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory uncorrectable ECC error occurred"
      ::= { hwMemory 17 }

    hwUncorrectableECCDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory uncorrectable ECC error deassert"
      ::= { hwMemory 18 }

    hwMemoryECCLimitation NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory correctable ECC logging limit reached detected"
      ::= { hwMemory 81 }

    hwMemoryECCLimitationDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory correctable ECC logging limit reached deassert"
      ::= { hwMemory 82 }


    hwMemoryPresence NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory presence detected"
      ::= { hwMemory 97 }

    hwMemoryPresenceDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory presence deassert"
      ::= { hwMemory 98 }


    hwMemoryCfgError NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory config error detected"
      ::= { hwMemory 113 }

    hwMemoryCfgErrorDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory config error deassert"
      ::= { hwMemory 114 }

    hwMemorySpare NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory spare detected"
      ::= { hwMemory 129 }

    hwMemorySpareDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory spare deassert"
      ::= { hwMemory 130 }

    hwMemoryOvertemp NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory overtemperature detected"
      ::= { hwMemory 161 }

    hwMemoryOvertempDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "memory overtemperature deassert"
      ::= { hwMemory 162 }

	
    hwStorageDevice OBJECT IDENTIFIER ::= {hwServerTRAPObject 13}
    
    hwStorageDevicePresence NOTIFICATION-TYPE
      OBJECTS { hwTrapSeq, hwTrapSensorName, hwTrapEvent, hwTrapSeverity, hwTrapEventCode, hwTrapServerIdentity, hwTrapLocation, hwTrapTime }
      STATUS  current
      DESCRIPTION
              "Storage device presence detected"
      ::= { hwStorageDevice 1 }

    hwStorageDevicePresenceDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Storage device presence deassert"
      ::= { hwStorageDevice 2 }

     hwStorageDeviceFault NOTIFICATION-TYPE
      OBJECTS { hwTrapSeq, hwTrapSensorName, hwTrapEvent, hwTrapSeverity, hwTrapEventCode, hwTrapServerIdentity, hwTrapLocation, hwTrapTime }
      STATUS  current
      DESCRIPTION
              "Storage device fault detected"
      ::= { hwStorageDevice 17 }

    hwStorageDeviceFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Storage device fault deassert"
      ::= { hwStorageDevice 18 }

    hwStorageDevicePredictiveFailure NOTIFICATION-TYPE
      OBJECTS { hwTrapSeq, hwTrapSensorName, hwTrapEvent, hwTrapSeverity, hwTrapEventCode, hwTrapServerIdentity, hwTrapLocation, hwTrapTime }
      STATUS  current
      DESCRIPTION
              "Storage device predictive failure"
      ::= { hwStorageDevice 33 }

    hwStorageDevicePredictiveFailureDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Storage device predictive failure deassert"
      ::= { hwStorageDevice 34 }
	  
    hwRAIDArrayFail NOTIFICATION-TYPE
      OBJECTS { hwTrapSeq, hwTrapSensorName, hwTrapEvent, hwTrapSeverity, hwTrapEventCode, hwTrapServerIdentity, hwTrapLocation, hwTrapTime }
      STATUS  current
      DESCRIPTION
              "RAID array fail detected"
      ::= { hwStorageDevice 97 }

    hwRAIDArrayFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID array fail deassert"
      ::= { hwStorageDevice 98 }

	hwRAIDRebuild NOTIFICATION-TYPE
      OBJECTS { hwTrapSeq, hwTrapSensorName, hwTrapEvent, hwTrapSeverity, hwTrapEventCode, hwTrapServerIdentity, hwTrapLocation, hwTrapTime }
      STATUS  current
      DESCRIPTION
              "RAID rebuild detected"
      ::= { hwStorageDevice 113 }

    hwRAIDRebuildDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID rebuild deassert"
      ::= { hwStorageDevice 114 }
	  
	hwRAIDRebuildAborted NOTIFICATION-TYPE
      OBJECTS { hwTrapSeq, hwTrapSensorName, hwTrapEvent, hwTrapSeverity, hwTrapEventCode, hwTrapServerIdentity, hwTrapLocation, hwTrapTime }
      STATUS  current
      DESCRIPTION
              "RAID rebuild aborted detected"
      ::= { hwStorageDevice 129 }
	  
	hwRAIDRebuildAbortedDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID rebuild aborted deassert"
      ::= { hwStorageDevice 130 }
 	
    hwSysFWProgress OBJECT IDENTIFIER ::= {hwServerTRAPObject 15} 
    
    hwSystemFirmwareHang NOTIFICATION-TYPE
      OBJECTS { hwTrapSeq, hwTrapSensorName, hwTrapEvent, hwTrapSeverity, hwTrapEventCode, hwTrapServerIdentity, hwTrapLocation, hwTrapTime }
      STATUS  current
      DESCRIPTION
              "System firmware hang"
      ::= { hwSysFWProgress 17 }

    hwSystemFirmwareHangDeassert NOTIFICATION-TYPE
      OBJECTS { hwTrapSeq, hwTrapSensorName, hwTrapEvent, hwTrapSeverity, hwTrapEventCode, hwTrapServerIdentity, hwTrapLocation, hwTrapTime }
      STATUS  current
      DESCRIPTION
              "System firmware hang deassert"
      ::= { hwSysFWProgress 18 }
    
    hwPS2USBFault NOTIFICATION-TYPE
      OBJECTS { hwTrapSeq, hwTrapSensorName, hwTrapEvent, hwTrapSeverity, hwTrapEventCode, hwTrapServerIdentity, hwTrapLocation, hwTrapTime }
      STATUS  current
      DESCRIPTION
              "Unrecoverable PS/2 or USB keyboard failure"
      ::= { hwSysFWProgress 1793 }

    hwPS2USBFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Unrecoverable PS/2 or USB keyboard failure deassert"
      ::= { hwSysFWProgress 1794 }

    hwVideoControllerFault NOTIFICATION-TYPE
      OBJECTS { hwTrapSeq, hwTrapSensorName, hwTrapEvent, hwTrapSeverity, hwTrapEventCode, hwTrapServerIdentity, hwTrapLocation, hwTrapTime }
      STATUS  current
      DESCRIPTION
              "Unrecoverable video controller failure"
      ::= { hwSysFWProgress 2305 }

    hwVideoControllerFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Unrecoverable video controller failure deassert"
      ::= { hwSysFWProgress 2306 }

    hwCPUVoltageMismatch NOTIFICATION-TYPE
      OBJECTS { hwTrapSeq, hwTrapSensorName, hwTrapEvent, hwTrapSeverity, hwTrapEventCode, hwTrapServerIdentity, hwTrapLocation, hwTrapTime }
      STATUS  current
      DESCRIPTION
              "CPU voltage mismatch"
      ::= { hwSysFWProgress 3073 }

    hwCPUVoltageMismatchDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU voltage mismatch deassert"
      ::= { hwSysFWProgress 3074 }

    hwSystemNoMemory NOTIFICATION-TYPE
      OBJECTS { hwTrapSeq, hwTrapSensorName, hwTrapEvent, hwTrapSeverity, hwTrapEventCode, hwTrapServerIdentity, hwTrapLocation, hwTrapTime }
      STATUS  current
      DESCRIPTION
              "System no memory detected"
      ::= { hwSysFWProgress 257 }

    hwSystemNoMemoryDeassert NOTIFICATION-TYPE
      OBJECTS { hwTrapSeq, hwTrapSensorName, hwTrapEvent, hwTrapSeverity, hwTrapEventCode, hwTrapServerIdentity, hwTrapLocation, hwTrapTime }
      STATUS  current
      DESCRIPTION
              "System no memory detected deassert"
      ::= { hwSysFWProgress 258 }
      

 	
    hwSysEvent OBJECT IDENTIFIER ::= {hwServerTRAPObject 18} 
    
    hwSysEventInstance NOTIFICATION-TYPE
      OBJECTS { hwTrapSeq, hwTrapSensorName, hwTrapEvent, hwTrapSeverity, hwTrapEventCode, hwTrapServerIdentity, hwTrapLocation, hwTrapTime }
      STATUS  current
      DESCRIPTION
              "PEF action"
      ::= { hwSysEvent 65 }

    hwSystemError NOTIFICATION-TYPE
      OBJECTS { hwTrapSeq, hwTrapSensorName, hwTrapEvent, hwTrapSeverity, hwTrapEventCode, hwTrapServerIdentity, hwTrapLocation, hwTrapTime }
      STATUS  current
      DESCRIPTION
              "System hang up/reset. For more information, see the background log"
      ::= { hwSysEvent 33 }

    hwSystemErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "System hang up/reset deassert"
      ::= { hwSysEvent 34 }
 	
    hwPowerButton OBJECT IDENTIFIER ::= {hwServerTRAPObject 20}                         

    hwPowerButtonPressed NOTIFICATION-TYPE
      OBJECTS { hwTrapSeq, hwTrapSensorName, hwTrapEvent, hwTrapSeverity, hwTrapEventCode, hwTrapServerIdentity, hwTrapLocation, hwTrapTime }
      STATUS  current
      DESCRIPTION
              "Power button pressed"
      ::= { hwPowerButton 1 }


	
    hwCable OBJECT IDENTIFIER ::= {hwServerTRAPObject 27}
    
    hwCableStatus NOTIFICATION-TYPE
      OBJECTS { hwTrapSeq, hwTrapSensorName, hwTrapEvent, hwTrapSeverity, hwTrapEventCode, hwTrapServerIdentity, hwTrapLocation, hwTrapTime }
      STATUS  current
      DESCRIPTION
              "SAS or Harddisk backplane cable config error"
      ::= { hwCable 17 }

    hwCableStatusDeassert NOTIFICATION-TYPE
      OBJECTS { hwTrapSeq, hwTrapSensorName, hwTrapEvent, hwTrapSeverity, hwTrapEventCode, hwTrapServerIdentity, hwTrapLocation, hwTrapTime }
      STATUS  current
      DESCRIPTION
              "SAS or Harddisk backplane cable config error deassert"
      ::= { hwCable 18 }


	
    hwSysRestart OBJECT IDENTIFIER ::= {hwServerTRAPObject 29}
    
    hwSysRestartUnknown NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause unknown"
      ::= { hwSysRestart 113 }

    hwSysRestartChassisCtrl NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause chassis control"
      ::= { hwSysRestart 369 }

    hwSysRestartPowerButton NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause power button pressed"
      ::= { hwSysRestart 881 }


    hwSysRestartWatchdogCtrl NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause Watchdog control"
      ::= { hwSysRestart 1137 }
      
    hwSysRestartAlwaysRestore NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause always power up"
      ::= { hwSysRestart 1649 }

    hwSysRestartRestorePrevState NOTIFICATION-TYPE
      OBJECTS { hwTrapSeq, hwTrapSensorName, hwTrapEvent, hwTrapSeverity, hwTrapEventCode, hwTrapServerIdentity, hwTrapLocation, hwTrapTime }
      STATUS  current
      DESCRIPTION
              "system restart cause always restore previous state"
      ::= { hwSysRestart 1905 }
	
    hwBootError OBJECT IDENTIFIER ::= {hwServerTRAPObject 30}
    
    hwNoBootableMedia NOTIFICATION-TYPE
      OBJECTS { hwTrapSeq, hwTrapSensorName, hwTrapEvent, hwTrapSeverity, hwTrapEventCode, hwTrapServerIdentity, hwTrapLocation, hwTrapTime }
      STATUS  current
      DESCRIPTION
              "boot error, no bootable media"
      ::= { hwBootError 1 }

    hwNoBootableMediaDeassert NOTIFICATION-TYPE
      OBJECTS { hwTrapSeq, hwTrapSensorName, hwTrapEvent, hwTrapSeverity, hwTrapEventCode, hwTrapServerIdentity, hwTrapLocation, hwTrapTime }
      STATUS  current
      DESCRIPTION
              "boot error, no bootable media deassert"
      ::= { hwBootError 2 }

    hwNoBootableDisk NOTIFICATION-TYPE
      OBJECTS { hwTrapSeq, hwTrapSensorName, hwTrapEvent, hwTrapSeverity, hwTrapEventCode, hwTrapServerIdentity, hwTrapLocation, hwTrapTime }
      STATUS  current
      DESCRIPTION
              "boot error, Non-bootable disk in drive"
      ::= { hwBootError 17 }

    hwNoBootableDiskDeassert NOTIFICATION-TYPE
      OBJECTS { hwTrapSeq, hwTrapSensorName, hwTrapEvent, hwTrapSeverity, hwTrapEventCode, hwTrapServerIdentity, hwTrapLocation, hwTrapTime }
      STATUS  current
      DESCRIPTION
              "boot error, Non-bootable disk in drive deassert"
      ::= { hwBootError 18 }

    hwPXENotFound NOTIFICATION-TYPE
      OBJECTS { hwTrapSeq, hwTrapSensorName, hwTrapEvent, hwTrapSeverity, hwTrapEventCode, hwTrapServerIdentity, hwTrapLocation, hwTrapTime }
      STATUS  current
      DESCRIPTION
              "boot error, PXE server not found"
      ::= { hwBootError 33 }

    hwPXENotFoundDeassert NOTIFICATION-TYPE
      OBJECTS { hwTrapSeq, hwTrapSensorName, hwTrapEvent, hwTrapSeverity, hwTrapEventCode, hwTrapServerIdentity, hwTrapLocation, hwTrapTime }
      STATUS  current
      DESCRIPTION
              "boot error, PXE server not found deassert"
      ::= { hwBootError 34 }


    hwInvalidBootSector NOTIFICATION-TYPE
      OBJECTS { hwTrapSeq, hwTrapSensorName, hwTrapEvent, hwTrapSeverity, hwTrapEventCode, hwTrapServerIdentity, hwTrapLocation, hwTrapTime }
      STATUS  current
      DESCRIPTION
              "boot error, Invalid boot sector"
      ::= { hwBootError 49 }

    hwInvalidBootSectorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "boot error, Invalid boot sector deassert"
      ::= { hwBootError 50 }

	
 	
    hwDeviceFault OBJECT IDENTIFIER ::= {hwServerTRAPObject 33}
    
    
    hwHardwareAddrFault NOTIFICATION-TYPE
      OBJECTS { hwTrapSeq, hwTrapSensorName, hwTrapEvent, hwTrapSeverity, hwTrapEventCode, hwTrapServerIdentity, hwTrapLocation, hwTrapTime }
      STATUS  current
      DESCRIPTION
              "Hardware address in fault status"
      ::= { hwDeviceFault 1 }


    hwHardwareAddrFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Hardware address in fault status deassert"
      ::= { hwDeviceFault 2 }

    hwLossBmaHeartBeat NOTIFICATION-TYPE
      OBJECTS { hwTrapSeq, hwTrapSensorName, hwTrapEvent, hwTrapSeverity, hwTrapEventCode, hwTrapServerIdentity, hwTrapLocation, hwTrapTime }
      STATUS  current
      DESCRIPTION
              "Heartbeat signals between the iBMC and iBMA are lost"
      ::= { hwDeviceFault 17 }


    hwLossBmaHeartBeatDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Heartbeat signals between the iBMC and iBMA are normal"
      ::= { hwDeviceFault 18 }
	  
    hwDeviceInstall NOTIFICATION-TYPE
      OBJECTS { hwTrapSeq, hwTrapSensorName, hwTrapEvent, hwTrapSeverity, hwTrapEventCode, hwTrapServerIdentity, hwTrapLocation, hwTrapTime }
      STATUS  current
      DESCRIPTION
              "Device installed"
      ::= { hwDeviceFault 33 }


    hwDeviceInstallDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Device installed deassert"
      ::= { hwDeviceFault 34 }   
     
    hwEthLinkDown NOTIFICATION-TYPE
      OBJECTS { hwTrapSeq, hwTrapSensorName, hwTrapEvent, hwTrapSeverity, hwTrapEventCode, hwTrapServerIdentity, hwTrapLocation, hwTrapTime }
      STATUS  current
      DESCRIPTION
              "System Eth link down"
      ::= { hwDeviceFault 129 }


    hwEthLinkDownDeassert NOTIFICATION-TYPE
      OBJECTS { hwTrapSeq, hwTrapSensorName, hwTrapEvent, hwTrapSeverity, hwTrapEventCode, hwTrapServerIdentity, hwTrapLocation, hwTrapTime }
      STATUS  current
      DESCRIPTION
              "System Eth link down deassert"
      ::= { hwDeviceFault 130 } 
      
      
	hwMemBrdMigrate NOTIFICATION-TYPE
      OBJECTS { hwTrapSeq, hwTrapSensorName, hwTrapEvent, hwTrapSeverity, hwTrapEventCode, hwTrapServerIdentity, hwTrapLocation, hwTrapTime }
      STATUS  current
      DESCRIPTION
              "Spare Device"
      ::= { hwDeviceFault 145 } 
	  
	hwMemBrdMigrateDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Spare Device deassert"
      ::= { hwDeviceFault 146 } 
	  
	hwPCIEStatus NOTIFICATION-TYPE
      OBJECTS { hwTrapSeq, hwTrapSensorName, hwTrapEvent, hwTrapSeverity, hwTrapEventCode, hwTrapServerIdentity, hwTrapLocation, hwTrapTime }
      STATUS  current
      DESCRIPTION
              "PCIe Error"
      ::= { hwDeviceFault 257 } 
	  
	hwPCIEStatusDeassert NOTIFICATION-TYPE
      OBJECTS { hwTrapSeq, hwTrapSensorName, hwTrapEvent, hwTrapSeverity, hwTrapEventCode, hwTrapServerIdentity, hwTrapLocation, hwTrapTime }
      STATUS  current
      DESCRIPTION
              "PCIe Error deassert"
      ::= { hwDeviceFault 258 } 
      
    hwFanFault NOTIFICATION-TYPE
      OBJECTS { hwTrapSeq, hwTrapSensorName, hwTrapEvent, hwTrapSeverity, hwTrapEventCode, hwTrapServerIdentity, hwTrapLocation, hwTrapTime }
      STATUS  current
      DESCRIPTION
              "fan in fault status"
      ::= { hwDeviceFault 2049 }

    hwFanFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "fan in fault status deassert"
      ::= { hwDeviceFault 2050 }

    hwPCIeFault NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "PCIe in fault status"
      ::= { hwDeviceFault 2305 }

    hwPCIeFaultDeassert NOTIFICATION-TYPE
      OBJECTS { hwTrapSeq, hwTrapSensorName, hwTrapEvent, hwTrapSeverity, hwTrapEventCode, hwTrapEventData2, hwTrapEventData3, hwTrapServerIdentity, hwTrapLocation, hwTrapTime }
      STATUS  current
      DESCRIPTION
              "PCIe in fault status deassert"
      ::= { hwDeviceFault 2306 } 



	
    hwACPIStatus OBJECT IDENTIFIER ::= {hwServerTRAPObject 34}                         
    
    hwACPIStatusS0 NOTIFICATION-TYPE
      OBJECTS { hwTrapSeq, hwTrapSensorName, hwTrapEvent, hwTrapSeverity, hwTrapEventCode, hwTrapServerIdentity, hwTrapLocation, hwTrapTime }
      STATUS  current
      DESCRIPTION
              "ACPI status S0"
      ::= { hwACPIStatus 1 }

    hwACPIStatusS4S5 NOTIFICATION-TYPE
      OBJECTS { hwTrapSeq, hwTrapSensorName, hwTrapEvent, hwTrapSeverity, hwTrapEventCode, hwTrapServerIdentity, hwTrapLocation, hwTrapTime }
      STATUS  current
      DESCRIPTION
              "ACPI status, S4/S5 soft-off, particular when S4/S5 state cannot be determined"
      ::= { hwACPIStatus 97 }

	
    hwWatchDog OBJECT IDENTIFIER ::= {hwServerTRAPObject 35}
    
    hwWatchDogOverflow NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, no action"
      ::= { hwWatchDog 1 }

     hwWatchDogOverflowDeassert NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, no action deassert"
      ::= { hwWatchDog 2 }
      
     hwWatchDogReset NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, hard reset"
      ::= { hwWatchDog 17 }

     hwWatchDogResetDeassert NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, hard reset deassert"
      ::= { hwWatchDog 18 }

     hwWatchDogPowerDown NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, power down"
      ::= { hwWatchDog 33 }

     hwWatchDogPowerDownDeassert NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, power down deassert"
      ::= { hwWatchDog 34 }

     hwWatchDogPowerCycle NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, power cycle"
      ::= { hwWatchDog 49 }

     hwWatchDogPowerCycleDeassert NOTIFICATION-TYPE
      OBJECTS { hwTrapSeq, hwTrapSensorName, hwTrapEvent, hwTrapSeverity, hwTrapEventCode, hwTrapServerIdentity, hwTrapLocation, hwTrapTime }
      STATUS  current
      DESCRIPTION
              "watchdog overflow, power cycle deassert"
      ::= { hwWatchDog 50 }

	
    hwLANHeartBeat OBJECT IDENTIFIER ::= {hwServerTRAPObject 39}
    
    hwLANHeartLost NOTIFICATION-TYPE
      OBJECTS { hwTrapSeq, hwTrapSensorName, hwTrapEvent, hwTrapSeverity, hwTrapEventCode, hwTrapServerIdentity, hwTrapLocation, hwTrapTime }
      STATUS  current
      DESCRIPTION
              "LAN heart beat lost"
      ::= { hwLANHeartBeat 1 }

    hwLANHeartLostDeassert NOTIFICATION-TYPE
      OBJECTS { hwTrapSeq, hwTrapSensorName, hwTrapEvent, hwTrapSeverity, hwTrapEventCode, hwTrapServerIdentity, hwTrapLocation, hwTrapTime }
      STATUS  current
      DESCRIPTION
              "LAN heart beat lost deassert"
      ::= { hwLANHeartBeat 2 }

	
    hwMngmntHealth OBJECT IDENTIFIER ::= {hwServerTRAPObject 40}
    
    hwSensorAccessibleFail NOTIFICATION-TYPE
      OBJECTS { hwTrapSeq, hwTrapSensorName, hwTrapEvent, hwTrapSeverity, hwTrapEventCode, hwTrapServerIdentity, hwTrapLocation, hwTrapTime }
      STATUS  current
      DESCRIPTION
              "Sensor access degraded or unavailable"
      ::= { hwMngmntHealth 1 } 

    hwSensorAccessibleFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Sensor access degraded or unavailable deassert"
      ::= { hwMngmntHealth 2 }

    hwControllerAccessibleFail NOTIFICATION-TYPE
      OBJECTS { hwTrapSeq, hwTrapSensorName, hwTrapEvent, hwTrapSeverity, hwTrapEventCode, hwTrapServerIdentity, hwTrapLocation, hwTrapTime }
      STATUS  current
      DESCRIPTION
              "Controller access degraded or unavailable"
      ::= { hwMngmntHealth 17 } 

    hwControllerAccessibleFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Controller access degraded or unavailable deassert"
      ::= { hwMngmntHealth 18 }

    hwFruFail NOTIFICATION-TYPE
      OBJECTS { hwTrapSeq, hwTrapSensorName, hwTrapEvent, hwTrapSeverity, hwTrapEventCode, hwTrapServerIdentity, hwTrapLocation, hwTrapTime }
      STATUS  current
      DESCRIPTION
              "FRU failure"
      ::= { hwMngmntHealth 81 } 

    hwFruFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "FRU failure deassert"
      ::= { hwMngmntHealth 82 }

	
    hwBattery OBJECT IDENTIFIER ::= {hwServerTRAPObject 41} 
    
    hwRTCBatterylow NOTIFICATION-TYPE
      OBJECTS { hwTrapSeq, hwTrapSensorName, hwTrapEvent, hwTrapSeverity, hwTrapEventCode, hwTrapServerIdentity, hwTrapLocation, hwTrapTime }
      STATUS  current
      DESCRIPTION
              "RTC battery or RAID card BBU voltage low"
      ::= { hwBattery 1 }

    hwRTCBatterylowDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RTC battery or RAID card BBU voltage low deassert"
      ::= { hwBattery 2 }

    hwRAIDCardBBUFailed NOTIFICATION-TYPE
      OBJECTS { hwTrapSeq, hwTrapSensorName, hwTrapEvent, hwTrapSeverity, hwTrapEventCode, hwTrapServerIdentity, hwTrapLocation, hwTrapTime }
      STATUS  current
      DESCRIPTION
              "RAID card BBU failed"
      ::= { hwBattery 17 }

    hwRAIDCardBBUFailedDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID card BBU failure deassert"
      ::= { hwBattery 18 } 
	  
    hwRAIDCardBBUPresence NOTIFICATION-TYPE
      OBJECTS { hwTrapSeq, hwTrapSensorName, hwTrapEvent, hwTrapSeverity, hwTrapEventCode, hwTrapServerIdentity, hwTrapLocation, hwTrapTime }
      STATUS  current
      DESCRIPTION
              "RAID card BBU is present"
      ::= { hwBattery 33 }

    hwRAIDCardBBUPresenceDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID card BBU is absent"
      ::= { hwBattery 34 }
	  
    hwVerChange OBJECT IDENTIFIER ::= {hwServerTRAPObject 43} 
    
    hwHardwareChange NOTIFICATION-TYPE
      OBJECTS { hwTrapSeq, hwTrapSensorName, hwTrapEvent, hwTrapSeverity, hwTrapEventCode, hwTrapServerIdentity, hwTrapLocation, hwTrapTime }
      STATUS  current
      DESCRIPTION
              "Hardware change detected with associated Entity"
      ::= { hwVerChange 1 }

    hwFirmwareChange NOTIFICATION-TYPE
      OBJECTS { hwTrapSeq, hwTrapSensorName, hwTrapEvent, hwTrapSeverity, hwTrapEventCode, hwTrapServerIdentity, hwTrapLocation, hwTrapTime }
      STATUS  current
      DESCRIPTION
              "Firmware or software change detected with associated Entity"
      ::= { hwVerChange 17 }
	  
    hwLCD OBJECT IDENTIFIER ::= {hwServerTRAPObject 1052}  
    
    hwLCDFault NOTIFICATION-TYPE
      OBJECTS { hwTrapSeq, hwTrapSensorName, hwTrapEvent, hwTrapSeverity, hwTrapEventCode, hwTrapServerIdentity, hwTrapLocation, hwTrapTime }
      STATUS  current
      DESCRIPTION
              "LCD fault "
      ::= { hwLCD 17 }

    hwLCDFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "LCD fault deassert"
      ::= { hwLCD 18 }


	
    hwHotSwap OBJECT IDENTIFIER ::= {hwServerTRAPObject 240}
    
    hwHotSwaptoM0 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M0 status"
      ::= { hwHotSwap 1 }

    hwHotSwaptoM1 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M1 status"
      ::= { hwHotSwap 17 }

    hwHotSwaptoM2 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M2 status"
      ::= { hwHotSwap 33 }

    hwHotSwaptoM3 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M3 status"
      ::= { hwHotSwap 49 }

    hwHotSwaptoM4 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M4 status"
      ::= { hwHotSwap 65 }

    hwHotSwaptoM5 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M5 status"
      ::= { hwHotSwap 81 }

    hwHotSwaptoM6 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M6 status"
      ::= { hwHotSwap 97 }

    hwHotSwaptoM7 NOTIFICATION-TYPE
      OBJECTS { hwTrapSeq, hwTrapSensorName, hwTrapEvent, hwTrapSeverity, hwTrapEventCode, hwTrapServerIdentity, hwTrapLocation, hwTrapTime }
      STATUS  current
      DESCRIPTION
              "fru hot swap to M7 status"
      ::= { hwHotSwap 113 }

	
    hwIPMBLink OBJECT IDENTIFIER ::= {hwServerTRAPObject 241}
    
    hwIPMBLinkStateAll NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A disabled. IPMB-B disabled"
      ::= { hwIPMBLink 1 }

    hwIPMBLinkStateAllDeassert NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A disabled. IPMB-B disabled deassert"
      ::= { hwIPMBLink 2 }
      
    hwIPMBLinkStateB NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A enabled.IPMB-B disabled"
      ::= { hwIPMBLink 17 }

    hwIPMBLinkStateBDeassert NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A enabled.IPMB-B disabled deassert"
      ::= { hwIPMBLink 18 }

    hwIPMBLinkStateA NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A disabled.IPMB-B enabled"
      ::= { hwIPMBLink 33 }

    hwIPMBLinkStateADeassert NOTIFICATION-TYPE
      OBJECTS { hwTrapSeq, hwTrapSensorName, hwTrapEvent, hwTrapSeverity, hwTrapEventCode, hwTrapServerIdentity, hwTrapLocation, hwTrapTime }
      STATUS  current
      DESCRIPTION
              "IPMB-A disabled.IPMB-B enabled deassert"
      ::= { hwIPMBLink 34 }

    hwIPMBLinkStateNoFault NOTIFICATION-TYPE
      OBJECTS { hwTrapSeq, hwTrapSensorName, hwTrapEvent, hwTrapSeverity, hwTrapEventCode, hwTrapServerIdentity, hwTrapLocation, hwTrapTime }
      STATUS  current
      DESCRIPTION
              "IPMB bus no fault"
      ::= { hwIPMBLink 49 }
      
	
    hwTrapTest OBJECT IDENTIFIER ::= {hwServerTRAPObject 256}                         
    hwTrapTestInstance NOTIFICATION-TYPE
      OBJECTS { hwTrapSeq, hwTrapSensorName, hwTrapEvent, hwTrapSeverity, hwTrapEventCode, hwTrapServerIdentity, hwTrapLocation, hwTrapTime }
      STATUS  current
      DESCRIPTION
              "trap test"
      ::= { hwTrapTest 1 }
      
	
    hwOvertemperature OBJECT IDENTIFIER ::= {hwServerTRAPObject 257}
                             
    hwOvertempMinor NOTIFICATION-TYPE
      OBJECTS { hwTrapSeq, hwTrapSensorName, hwTrapEvent, hwTrapSeverity, hwTrapEventCode, hwTrapServerIdentity, hwTrapLocation, hwTrapTime }
      STATUS  current
      DESCRIPTION
              "temperature above minor threshold"
      ::= { hwOvertemperature 113 }  
      
     hwOvertempMinorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "temperature above minor threshold deassert"
      ::= { hwOvertemperature 114 }  
      
     hwOvertempMajor NOTIFICATION-TYPE
      OBJECTS { hwTrapSeq, hwTrapSensorName, hwTrapEvent, hwTrapSeverity, hwTrapEventCode, hwTrapServerIdentity, hwTrapLocation, hwTrapTime }
      STATUS  current
      DESCRIPTION
              "temperature above major threshold"
      ::= { hwOvertemperature 145 }  
      
     hwOvertempMajorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "temperature above major threshold deassert"
      ::= { hwOvertemperature 146 }  
      
     hwOvertempCritical NOTIFICATION-TYPE
      OBJECTS { hwTrapSeq, hwTrapSensorName, hwTrapEvent, hwTrapSeverity, hwTrapEventCode, hwTrapServerIdentity, hwTrapLocation, hwTrapTime }
      STATUS  current
      DESCRIPTION
              "temperature above critical threshold"
      ::= { hwOvertemperature 177 }  
      
     hwOvertempCriticalDeassert NOTIFICATION-TYPE
      OBJECTS { hwTrapSeq, hwTrapSensorName, hwTrapEvent, hwTrapSeverity, hwTrapEventCode, hwTrapServerIdentity, hwTrapLocation, hwTrapTime }
      STATUS  current
      DESCRIPTION
              "temperature above critical threshold deassert"
      ::= { hwOvertemperature 178 }


    hwNoSDCard OBJECT IDENTIFIER ::= {hwServerTRAPObject 781}  
    
    hwNoSDCardAssert NOTIFICATION-TYPE
      OBJECTS { hwTrapSeq, hwTrapSensorName, hwTrapEvent, hwTrapSeverity, hwTrapEventCode, hwTrapServerIdentity, hwTrapLocation, hwTrapTime }
      STATUS  current
      DESCRIPTION
              "No SD Card Assert"
      ::= { hwNoSDCard 17 }
	  
    hwNoSDCardDeassert NOTIFICATION-TYPE
      OBJECTS { hwTrapSeq, hwTrapSensorName, hwTrapEvent, hwTrapSeverity, hwTrapEventCode, hwTrapServerIdentity, hwTrapLocation, hwTrapTime }
      STATUS  current
      DESCRIPTION
              "No SD Card Deassert"
      ::= { hwNoSDCard 18 }
            
    hwBoardMismatch OBJECT IDENTIFIER ::= {hwServerTRAPObject 786}  
		
    hwBoardMismatchAssert NOTIFICATION-TYPE
      OBJECTS { hwTrapSeq, hwTrapSensorName, hwTrapEvent, hwTrapSeverity, hwTrapEventCode, hwTrapServerIdentity, hwTrapLocation, hwTrapTime }
      STATUS  current
      DESCRIPTION
              "Board Mismatch Assert"
      ::= { hwBoardMismatch 17 }
	  
    hwBoardMismatchDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Board Mismatch Deassert"
      ::= { hwBoardMismatch 18 }
    
    hwAddInCard OBJECT IDENTIFIER ::= {hwServerTRAPObject 791}  
    
    hwPCIeError NOTIFICATION-TYPE
      OBJECTS { hwTrapSeq, hwTrapSensorName, hwTrapEvent, hwTrapSeverity, hwTrapEventCode, hwTrapServerIdentity, hwTrapLocation, hwTrapTime }
      STATUS  current
      DESCRIPTION
              "PCIe Error"
      ::= { hwAddInCard 17 }
	  
    hwPCIeErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "PCIe Error Deassert"
      ::= { hwAddInCard 18 }
	  
    hwChipSet OBJECT IDENTIFIER ::= {hwServerTRAPObject 793}  
    
    hwPCHError NOTIFICATION-TYPE
      OBJECTS { hwTrapSeq, hwTrapSensorName, hwTrapEvent, hwTrapSeverity, hwTrapEventCode, hwTrapServerIdentity, hwTrapLocation, hwTrapTime }
      STATUS  current
      DESCRIPTION
              "Uncorrectable PCH error"
      ::= { hwChipSet 17 }
	  
    hwPCHErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Uncorrectable PCH error Deassert"
      ::= { hwChipSet 18 }
	
    hwUIDButton OBJECT IDENTIFIER ::= {hwServerTRAPObject 788}  
    
    hwUIDButtonPressed NOTIFICATION-TYPE
      OBJECTS { hwTrapSeq, hwTrapSensorName, hwTrapEvent, hwTrapSeverity, hwTrapEventCode, hwTrapServerIdentity, hwTrapLocation, hwTrapTime }
      STATUS  current
      DESCRIPTION
              "UID button pressed"
      ::= { hwUIDButton 17 }


	
    hwPowerCapping OBJECT IDENTIFIER ::= {hwServerTRAPObject 1042}  
    
    hwPowerCapFail NOTIFICATION-TYPE
      OBJECTS { hwTrapSeq, hwTrapSensorName, hwTrapEvent, hwTrapSeverity, hwTrapEventCode, hwTrapServerIdentity, hwTrapLocation, hwTrapTime }
      STATUS  current
      DESCRIPTION
              "Power capping fail assert"
      ::= { hwPowerCapping 17 }

    hwPowerCapFailDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Power capping fail deassert"
      ::= { hwPowerCapping 18 }

	
    hwCardFault OBJECT IDENTIFIER ::= {hwServerTRAPObject 1047}  
    
    hwCardStatusFault NOTIFICATION-TYPE
      OBJECTS { hwTrapSeq, hwTrapSensorName, hwTrapEvent, hwTrapSeverity, hwTrapEventCode, hwTrapServerIdentity, hwTrapLocation, hwTrapTime }
      STATUS  current
      DESCRIPTION
              "RAID or NIC card fault"
      ::= { hwCardFault 17 }

    hwCardStatusFaultDeassert NOTIFICATION-TYPE
      OBJECTS { hwTrapSeq, hwTrapSensorName, hwTrapEvent, hwTrapSeverity, hwTrapEventCode, hwTrapServerIdentity, hwTrapLocation, hwTrapTime }
      STATUS  current
      DESCRIPTION
              "RAID or NIC card fault deassert"
      ::= { hwCardFault 18 }
      
    hwCPUUsage OBJECT IDENTIFIER ::= {hwServerTRAPObject 1287}  
    
    hwCPUUsageHigh NOTIFICATION-TYPE
      OBJECTS { hwTrapSeq, hwTrapSensorName, hwTrapEvent, hwTrapSeverity, hwTrapEventCode, hwTrapServerIdentity, hwTrapLocation, hwTrapTime }
      STATUS  current
      DESCRIPTION
              "CPU usage over threshold "
      ::= { hwCPUUsage 17 }

    hwCPUUsageHighDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU usage over threshold deassert"
      ::= { hwCPUUsage 18 }



    hwMemoryUsage OBJECT IDENTIFIER ::= {hwServerTRAPObject 1292}  
    
    hwMemoryUsageHigh NOTIFICATION-TYPE
      OBJECTS { hwTrapSeq, hwTrapSensorName, hwTrapEvent, hwTrapSeverity, hwTrapEventCode, hwTrapServerIdentity, hwTrapLocation, hwTrapTime }
      STATUS  current
      DESCRIPTION
              "Memory usage over threshold "
      ::= { hwMemoryUsage 17 }

    hwMemoryUsageHighDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory usage over threshold deassert"
      ::= { hwMemoryUsage 18 }


    hwDiskUsage OBJECT IDENTIFIER ::= {hwServerTRAPObject 1293}  
    
    hwDiskUsageHigh NOTIFICATION-TYPE
      OBJECTS { hwTrapSeq, hwTrapSensorName, hwTrapEvent, hwTrapSeverity, hwTrapEventCode, hwTrapServerIdentity, hwTrapLocation, hwTrapTime }
      STATUS  current
      DESCRIPTION
              "Disk usage over threshold "
      ::= { hwDiskUsage 17 }

    hwDiskUsageHighDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Disk usage over threshold deassert"
      ::= { hwDiskUsage 18 }
	  
    hwSysNotice OBJECT IDENTIFIER ::= {hwServerTRAPObject 1810}  
    
    hwSystemWarmReset NOTIFICATION-TYPE
      OBJECTS { hwTrapSeq, hwTrapSensorName, hwTrapEvent, hwTrapSeverity, hwTrapEventCode, hwTrapServerIdentity, hwTrapLocation, hwTrapTime }
      STATUS  current
      DESCRIPTION
              "Uncorrectable system error. Unable to locate the specific failure, please warm reset the host to try to solve the problem"
      ::= { hwSysNotice 129 }
	  
    hwSystemWarmResetDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Uncorrectable system error deassert"
      ::= { hwSysNotice 130 }
     
    hwModule OBJECT IDENTIFIER ::= {hwServerTRAPObject 1813}  
    
    hwModuleCritical NOTIFICATION-TYPE
      OBJECTS { hwTrapSeq, hwTrapSensorName, hwTrapEvent, hwTrapSeverity, hwTrapEventCode, hwTrapServerIdentity, hwTrapLocation, hwTrapTime }
      STATUS  current
      DESCRIPTION
              "transition to Critical from less severe"
      ::= { hwModule 33 }
	
    hwPSPresenceStatus OBJECT IDENTIFIER ::= {hwServerTRAPObject 2057}  
    
    hwPSPresence NOTIFICATION-TYPE
      OBJECTS { hwTrapSeq, hwTrapSensorName, hwTrapEvent, hwTrapSeverity, hwTrapEventCode, hwTrapServerIdentity, hwTrapLocation, hwTrapTime }
      STATUS  current
      DESCRIPTION
              "power supply presence "
      ::= { hwPSPresenceStatus 17 }

    hwPSPresenceDeassert NOTIFICATION-TYPE
      OBJECTS { hwTrapSeq, hwTrapSensorName, hwTrapEvent, hwTrapSeverity, hwTrapEventCode, hwTrapServerIdentity, hwTrapLocation, hwTrapTime }
      STATUS  current
      DESCRIPTION
              "power supply presence deassert"
      ::= { hwPSPresenceStatus 18 }
	
    hwFanPresenceStatus OBJECT IDENTIFIER ::= {hwServerTRAPObject 2058}  
    
    hwFanAbsent NOTIFICATION-TYPE
      OBJECTS { hwTrapSeq, hwTrapSensorName, hwTrapEvent, hwTrapSeverity, hwTrapEventCode, hwTrapServerIdentity, hwTrapLocation, hwTrapTime }
      STATUS  current
      DESCRIPTION
              "fan absent "
      ::= { hwFanPresenceStatus 1 }

    hwFanAbsentDeassert NOTIFICATION-TYPE
      OBJECTS { hwTrapSeq, hwTrapSensorName, hwTrapEvent, hwTrapSeverity, hwTrapEventCode, hwTrapServerIdentity, hwTrapLocation, hwTrapTime }
      STATUS  current
      DESCRIPTION
              "fan absent deassert"
      ::= { hwFanPresenceStatus 2 }     

	
    hwCardPresenceStatus OBJECT IDENTIFIER ::= {hwServerTRAPObject 2071}  
    
    hwCardPresence NOTIFICATION-TYPE
      OBJECTS { hwTrapSeq, hwTrapSensorName, hwTrapEvent, hwTrapSeverity, hwTrapEventCode, hwTrapServerIdentity, hwTrapLocation, hwTrapTime }
      STATUS  current
      DESCRIPTION
              "card presence "
      ::= { hwCardPresenceStatus 17 }

    hwCardPresenceDeassert NOTIFICATION-TYPE
      OBJECTS { hwTrapSeq, hwTrapSensorName, hwTrapEvent, hwTrapSeverity, hwTrapEventCode, hwTrapServerIdentity, hwTrapLocation, hwTrapTime }
      STATUS  current
      DESCRIPTION
              "card presence deassert"
      ::= { hwCardPresenceStatus 18 }  

    hwLCDPresenceStatus OBJECT IDENTIFIER ::= {hwServerTRAPObject 2076}  
    
    hwLCDAbsent NOTIFICATION-TYPE
      OBJECTS { hwTrapSeq, hwTrapSensorName, hwTrapEvent, hwTrapSeverity, hwTrapEventCode, hwTrapServerIdentity, hwTrapLocation, hwTrapTime }
      STATUS  current
      DESCRIPTION
              "LCD absent"
      ::= { hwLCDPresenceStatus 1 }

    hwLCDAbsentDeassert NOTIFICATION-TYPE
      OBJECTS { hwTrapSeq, hwTrapSensorName, hwTrapEvent, hwTrapSeverity, hwTrapEventCode, hwTrapServerIdentity, hwTrapLocation, hwTrapTime }
      STATUS  current
      DESCRIPTION
              "LCD absent deassert"
      ::= { hwLCDPresenceStatus 2 }  	  
	  
    hwMemoryRiser OBJECT IDENTIFIER ::= {hwServerTRAPObject 2583}    	
    hwMemoryRiserOnline NOTIFICATION-TYPE
      OBJECTS { hwTrapSeq, hwTrapSensorName, hwTrapEvent, hwTrapSeverity, hwTrapEventCode, hwTrapServerIdentity, hwTrapLocation, hwTrapTime }
      STATUS  current
      DESCRIPTION
              "Memory board online "
      ::= { hwMemoryRiser 49 }

    hwMemoryRiserOnlineDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory board online deassert"
      ::= { hwMemoryRiser 50 }

    hwMemoryRiserOffline NOTIFICATION-TYPE
      OBJECTS { hwTrapSeq, hwTrapSensorName, hwTrapEvent, hwTrapSeverity, hwTrapEventCode, hwTrapServerIdentity, hwTrapLocation, hwTrapTime }
      STATUS  current
      DESCRIPTION
              "Memory board offline "
      ::= { hwMemoryRiser 65 }

    hwMemoryRiserOfflineDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory board offline deassert"
      ::= { hwMemoryRiser 66 }
      
    hwMemoryRiserInstallError NOTIFICATION-TYPE
      OBJECTS { hwTrapSeq, hwTrapSensorName, hwTrapEvent, hwTrapSeverity, hwTrapEventCode, hwTrapServerIdentity, hwTrapLocation, hwTrapTime }
      STATUS  current
      DESCRIPTION
              "Memory riser install error "
      ::= { hwMemoryRiser 129 }

    hwMemoryRiserInstallErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory riser install error deassert"
      ::= { hwMemoryRiser 130 }

      
    hwCPUCore OBJECT IDENTIFIER ::= {hwServerTRAPObject 2311}
    
    hwCPUCoreIsolation NOTIFICATION-TYPE
      OBJECTS { hwTrapSeq, hwTrapSensorName, hwTrapEvent, hwTrapSeverity, hwTrapEventCode, hwTrapServerIdentity, hwTrapLocation, hwTrapTime }
      STATUS  current
      DESCRIPTION
              "CPU core isolation"
      ::= { hwCPUCore 1 }

    hwCPUCoreIsolationDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU core isolation deassert"
      ::= { hwCPUCore 2 }
	  
    hwPSRedundancy OBJECT IDENTIFIER ::= {hwServerTRAPObject 2824}
    
    hwPSRedundancyLost NOTIFICATION-TYPE
      OBJECTS { hwTrapSeq, hwTrapSensorName, hwTrapEvent, hwTrapSeverity, hwTrapEventCode, hwTrapServerIdentity, hwTrapLocation, hwTrapTime }
      STATUS  current
      DESCRIPTION
              "PS Redundancy lost"
      ::= { hwPSRedundancy 17 }

    hwPSRedundancyLostDeassert NOTIFICATION-TYPE
      OBJECTS { hwTrapSeq, hwTrapSensorName, hwTrapEvent, hwTrapSeverity, hwTrapEventCode, hwTrapServerIdentity, hwTrapLocation, hwTrapTime }
      STATUS  current
      DESCRIPTION
              "PS Redundancy lost deassert"
      ::= { hwPSRedundancy 18 }
      
    hwSELStatus OBJECT IDENTIFIER ::= {hwServerTRAPObject 16}  
    
    hwSELClearedAssert NOTIFICATION-TYPE
      OBJECTS { hwTrapSeq, hwTrapSensorName, hwTrapEvent, hwTrapSeverity, hwTrapEventCode, hwTrapServerIdentity, hwTrapLocation, hwTrapTime }
      STATUS  current
      DESCRIPTION
              "SEL log area is cleared"
      ::= { hwSELStatus 33 }
	  
    hwSELAlmostFullAssert NOTIFICATION-TYPE
      OBJECTS { hwTrapSeq, hwTrapSensorName, hwTrapEvent, hwTrapSeverity, hwTrapEventCode, hwTrapServerIdentity, hwTrapLocation, hwTrapTime }
      STATUS  current
      DESCRIPTION
              "SEL almost full assert"
      ::= { hwSELStatus 81 }

    hwSELAlmostFullDeassert NOTIFICATION-TYPE
      OBJECTS { hwTrapSeq, hwTrapSensorName, hwTrapEvent, hwTrapSeverity, hwTrapEventCode, hwTrapServerIdentity, hwTrapLocation, hwTrapTime }
      STATUS  current
      DESCRIPTION
              "SEL almost full deassert"
      ::= { hwSELStatus 82 }

    hwBMCBootUp OBJECT IDENTIFIER ::= {hwServerTRAPObject 2326}  
    
    hwBMCBootUpAssert NOTIFICATION-TYPE
      OBJECTS { hwTrapSeq, hwTrapSensorName, hwTrapEvent, hwTrapSeverity, hwTrapEventCode, hwTrapServerIdentity, hwTrapLocation, hwTrapTime }
      STATUS  current
      DESCRIPTION
              "BMC boot up"
      ::= { hwBMCBootUp 17 }

    hwLog OBJECT IDENTIFIER ::= {hwServerTRAPObject 1808}  
      
    hwLogFull NOTIFICATION-TYPE
      OBJECTS { hwTrapSeq, hwTrapSensorName, hwTrapEvent, hwTrapSeverity, hwTrapEventCode, hwTrapServerIdentity, hwTrapLocation, hwTrapTime }
      STATUS  current
      DESCRIPTION
              "Informational"
      ::= { hwLog 129 }

    hwLogFullDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Informational deassert"
      ::= { hwLog 130 }
	
    hwVoltage OBJECT IDENTIFIER ::= {hwServerTRAPObject 258} 

    hwLowerVoltageMajor NOTIFICATION-TYPE
      OBJECTS { hwTrapSeq, hwTrapSensorName, hwTrapEvent, hwTrapSeverity, hwTrapEventCode, hwTrapServerIdentity, hwTrapLocation, hwTrapTime }
      STATUS  current
      DESCRIPTION
              "Voltage below lower major threshold"
      ::= { hwVoltage 33 }  
      
    hwLowerVoltageMajorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Voltage below lower major threshold deassert"
      ::= { hwVoltage 34 }  

    hwOverVoltageMajor NOTIFICATION-TYPE
      OBJECTS { hwTrapSeq, hwTrapSensorName, hwTrapEvent, hwTrapSeverity, hwTrapEventCode, hwTrapServerIdentity, hwTrapLocation, hwTrapTime }
      STATUS  current
      DESCRIPTION
              "Voltage over upper major threshold"
      ::= { hwVoltage 145 }

    hwOverVoltageMajorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Voltage over upper major threshold deassert"
      ::= { hwVoltage 146 }
      
    hwOverVoltageCritcal NOTIFICATION-TYPE
      OBJECTS { hwTrapSeq, hwTrapSensorName, hwTrapEvent, hwTrapSeverity, hwTrapEventCode, hwTrapServerIdentity, hwTrapLocation, hwTrapTime }
      STATUS  current
      DESCRIPTION
              "Voltage over upper critcal threshold"
      ::= { hwVoltage 177 }

    hwOverVoltageCritcalDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Voltage over upper critcal threshold deassert"
      ::= { hwVoltage 178 }

    hwCPUProchot OBJECT IDENTIFIER ::= {hwServerTRAPObject 775} 

    hwCPUProchotState NOTIFICATION-TYPE
      OBJECTS { hwTrapSeq, hwTrapSensorName, hwTrapEvent, hwTrapSeverity, hwTrapEventCode, hwTrapServerIdentity, hwTrapLocation, hwTrapTime }
      STATUS  current
      DESCRIPTION
              "CPU Prochot state asserted"
      ::= { hwCPUProchot 17 }  
      
    hwCPUProchotStateDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU Prochot state deasserted"
      ::= { hwCPUProchot 18 }  
        
	hwServerTRAPObjectV2 OBJECT IDENTIFIER ::= { hwTrap 11 }

	hwPCIeCardEvent OBJECT IDENTIFIER ::= {hwServerTRAPObjectV2 9 }
    
		hwPCIeCardUncorrectableErr NOTIFICATION-TYPE
			OBJECTS { hwTrapSeq, hwTrapEvent,hwTrapSeverity,hwTrapServerIdentity, hwTrapLocation, hwTrapTime } 
			STATUS  current
			DESCRIPTION
				"PCIe card uncorrectable error"
			::= { hwPCIeCardEvent 1 }
			
		hwPCIeCardUncorrectableErrDeassert NOTIFICATION-TYPE
			OBJECTS { hwTrapSeq, hwTrapEvent,hwTrapSeverity,hwTrapServerIdentity, hwTrapLocation, hwTrapTime } 
			STATUS  current
			DESCRIPTION
				"PCIe card uncorrectable error deassert"
			::= { hwPCIeCardEvent 2 }
			
		hwPCIeCardOverTemp NOTIFICATION-TYPE
			OBJECTS { hwTrapSeq, hwTrapEvent,hwTrapSeverity,hwTrapServerIdentity, hwTrapLocation, hwTrapTime } 
			STATUS  current
			DESCRIPTION
				"PCIe card  temperature upper threshold"
			::= { hwPCIeCardEvent 3 }
			
		hwPCIeCardOverTempDeassert NOTIFICATION-TYPE
			OBJECTS { hwTrapSeq, hwTrapEvent,hwTrapSeverity,hwTrapServerIdentity, hwTrapLocation, hwTrapTime } 
			STATUS  current
			DESCRIPTION
				"PCIe card  temperature upper threshold deassert"
			::= { hwPCIeCardEvent 4 }	
			
		hwPCIeCardAccessTempFailure NOTIFICATION-TYPE
			OBJECTS { hwTrapSeq, hwTrapEvent,hwTrapSeverity,hwTrapServerIdentity, hwTrapLocation, hwTrapTime } 
			STATUS  current
			DESCRIPTION
				"Failed to obtain temperature of PCIe card"
			::= { hwPCIeCardEvent 5 }
			
		hwPCIeCardAccessTempFailureDeassert NOTIFICATION-TYPE
			OBJECTS { hwTrapSeq, hwTrapEvent,hwTrapSeverity,hwTrapServerIdentity, hwTrapLocation, hwTrapTime } 
			STATUS  current
			DESCRIPTION
				"Failed to obtain temperature of PCIe card deassert"
			::= { hwPCIeCardEvent 6 }
		hwPCIeCardAccessFRULableFailure NOTIFICATION-TYPE
			OBJECTS { hwTrapSeq, hwTrapEvent,hwTrapSeverity,hwTrapServerIdentity, hwTrapLocation, hwTrapTime } 
			STATUS  current
			DESCRIPTION
				"Failed to obtain electronic label of PCIe card"
			::= { hwPCIeCardEvent 7 }
		hwPCIeCardAccessFRULableFailureDeassert NOTIFICATION-TYPE
			OBJECTS { hwTrapSeq, hwTrapEvent,hwTrapSeverity,hwTrapServerIdentity, hwTrapLocation, hwTrapTime } 
			STATUS  current
			DESCRIPTION
				"Failed to obtain electronic label of PCIe card deassert"
			::= { hwPCIeCardEvent 8 }
		hwPCIeCardDIMMOverTemp NOTIFICATION-TYPE
			OBJECTS { hwTrapSeq, hwTrapEvent,hwTrapSeverity,hwTrapServerIdentity, hwTrapLocation, hwTrapTime } 
			STATUS  current
			DESCRIPTION
				"PCIe card exceeds the overtemperature threshold"
			::= { hwPCIeCardEvent 9 }	
		hwPCIeCardDIMMOverTempDeassert NOTIFICATION-TYPE
			OBJECTS { hwTrapSeq, hwTrapEvent,hwTrapSeverity,hwTrapServerIdentity, hwTrapLocation, hwTrapTime } 
			STATUS  current
			DESCRIPTION
				"PCIe card exceeds the overtemperature threshold deasserted"
			::= { hwPCIeCardEvent 10 }
		hwPCIeCardOverTempMajor NOTIFICATION-TYPE
			OBJECTS { hwTrapSeq, hwTrapEvent,hwTrapSeverity,hwTrapServerIdentity, hwTrapLocation, hwTrapTime } 
			STATUS  current
			DESCRIPTION
				"PCIe card temperature over major threshold"
			::= { hwPCIeCardEvent 11 }
		hwPCIeCardOverTempMajorDeassert NOTIFICATION-TYPE
			OBJECTS { hwTrapSeq, hwTrapEvent,hwTrapSeverity,hwTrapServerIdentity, hwTrapLocation, hwTrapTime } 
			STATUS  current
			DESCRIPTION
				"PCIe card temperature over major threshold deassert"
			::= { hwPCIeCardEvent 12 }
		hwPCIeCardCPUOverTempMinor NOTIFICATION-TYPE
			OBJECTS { hwTrapSeq, hwTrapEvent,hwTrapSeverity,hwTrapServerIdentity, hwTrapLocation, hwTrapTime } 
			STATUS  current
			DESCRIPTION
				"PCIe card CPU core temperature exceeds the overtemperature threshold"
			::= { hwPCIeCardEvent 13 }
		hwPCIeCardCPUOverTempMinorDeassert NOTIFICATION-TYPE
			OBJECTS { hwTrapSeq, hwTrapEvent,hwTrapSeverity,hwTrapServerIdentity, hwTrapLocation, hwTrapTime } 
			STATUS  current
			DESCRIPTION
				"PCIe card CPU core temperature exceeds the overtemperature threshold deasserted"
			::= { hwPCIeCardEvent 14 }
		hwPCIeCardCPUOverTempMajor NOTIFICATION-TYPE
			OBJECTS { hwTrapSeq, hwTrapEvent,hwTrapSeverity,hwTrapServerIdentity, hwTrapLocation, hwTrapTime } 
			STATUS  current
			DESCRIPTION
				"PCIe card CPU core temperature over major threshold"
			::= { hwPCIeCardEvent 15 }
		hwPCIeCardCPUOverTempMajorDeassert NOTIFICATION-TYPE
			OBJECTS { hwTrapSeq, hwTrapEvent,hwTrapSeverity,hwTrapServerIdentity, hwTrapLocation, hwTrapTime } 
			STATUS  current
			DESCRIPTION
				"The PCIe card CPU core temperature over major threshold deassert"
			::= { hwPCIeCardEvent 16 }
		hwPCIeCardBattLowerVoltMinor NOTIFICATION-TYPE
			OBJECTS { hwTrapSeq, hwTrapEvent,hwTrapSeverity,hwTrapServerIdentity, hwTrapLocation, hwTrapTime } 
			STATUS  current
			DESCRIPTION
				"PCIe card voltage is lower than the undervoltage threshold"
			::= { hwPCIeCardEvent 17 }
		hwPCIeCardBattLowerVoltMinorDeassert NOTIFICATION-TYPE
			OBJECTS { hwTrapSeq, hwTrapEvent,hwTrapSeverity,hwTrapServerIdentity, hwTrapLocation, hwTrapTime } 
			STATUS  current
			DESCRIPTION
				"PCIe card voltage is lower than the undervoltage threshold deasserted"
			::= { hwPCIeCardEvent 18 }
		hwPCIeCardLowerVoltMajor NOTIFICATION-TYPE
			OBJECTS { hwTrapSeq, hwTrapEvent,hwTrapSeverity,hwTrapServerIdentity, hwTrapLocation, hwTrapTime } 
			STATUS  current
			DESCRIPTION
				"PCIe card voltage is lower than the undervoltage threshold"
			::= { hwPCIeCardEvent 19 }			
		hwPCIeCardLowerVoltMajorDeassert NOTIFICATION-TYPE
			OBJECTS { hwTrapSeq, hwTrapEvent,hwTrapSeverity,hwTrapServerIdentity, hwTrapLocation, hwTrapTime } 
			STATUS  current
			DESCRIPTION
				"PCIe card voltage lower than the undervoltage threshold deasserted"
			::= { hwPCIeCardEvent 20 }	
		hwPCIeCardOverVoltMajor NOTIFICATION-TYPE
			OBJECTS { hwTrapSeq, hwTrapEvent,hwTrapSeverity,hwTrapServerIdentity, hwTrapLocation, hwTrapTime } 
			STATUS  current
			DESCRIPTION
				"PCIe card voltage exceeds the overvoltage threshold"
			::= { hwPCIeCardEvent 21 }
		hwPCIeCardOverVoltMajorDeassert NOTIFICATION-TYPE
			OBJECTS { hwTrapSeq, hwTrapEvent,hwTrapSeverity,hwTrapServerIdentity, hwTrapLocation, hwTrapTime } 
			STATUS  current
			DESCRIPTION
				"PCIe card voltage exceeds the overvoltage threshold deasserted"
			::= { hwPCIeCardEvent 22 }	
		hwPCIeCardAccessVoltFailure NOTIFICATION-TYPE
			OBJECTS { hwTrapSeq, hwTrapEvent,hwTrapSeverity,hwTrapServerIdentity, hwTrapLocation, hwTrapTime } 
			STATUS  current
			DESCRIPTION
				"Failed to obtain data of the The PCIe card voltage "
			::= { hwPCIeCardEvent 23 }	
		hwPCIeCardAccessVoltFailureDeassert NOTIFICATION-TYPE
			OBJECTS { hwTrapSeq, hwTrapEvent,hwTrapSeverity,hwTrapServerIdentity, hwTrapLocation, hwTrapTime } 
			STATUS  current
			DESCRIPTION
				"Failed to obtain data of the The PCIe card voltage deasserted"
			::= { hwPCIeCardEvent 24 }	
		hwPCIeCardBootEvent NOTIFICATION-TYPE
			OBJECTS { hwTrapSeq, hwTrapEvent,hwTrapSeverity,hwTrapServerIdentity, hwTrapLocation, hwTrapTime } 
			STATUS  current
			DESCRIPTION
				"PCIe card starting BIOS "
			::= { hwPCIeCardEvent 25 }
		hwPCIeCardBootEventDeassert NOTIFICATION-TYPE
			OBJECTS { hwTrapSeq, hwTrapEvent,hwTrapSeverity,hwTrapServerIdentity, hwTrapLocation, hwTrapTime } 
			STATUS  current
			DESCRIPTION
				"PCIe card starting OS"
			::= { hwPCIeCardEvent 26 }
		hwPCIeCardHardwareFailure NOTIFICATION-TYPE
			OBJECTS { hwTrapSeq, hwTrapEvent,hwTrapSeverity,hwTrapServerIdentity, hwTrapLocation, hwTrapTime } 
			STATUS  current
			DESCRIPTION
				"A hardware fault occurs in PCIe card"
			::= { hwPCIeCardEvent 27 }
		hwPCIeCardHardwareFailureDeassert NOTIFICATION-TYPE
			OBJECTS { hwTrapSeq, hwTrapEvent,hwTrapSeverity,hwTrapServerIdentity, hwTrapLocation, hwTrapTime } 
			STATUS  current
			DESCRIPTION
				"A hardware fault occurs in PCIe card deasserted"
			::= { hwPCIeCardEvent 28 }	
		hwPCIeCardBootDiskAbsent NOTIFICATION-TYPE
			OBJECTS { hwTrapSeq, hwTrapEvent,hwTrapSeverity,hwTrapServerIdentity, hwTrapLocation, hwTrapTime } 
			STATUS  current
			DESCRIPTION
				"PCIe card  boot disk  does not exist"
			::= { hwPCIeCardEvent 29 }				
		hwPCIeCardBootDiskAbsentDeassert NOTIFICATION-TYPE
			OBJECTS { hwTrapSeq, hwTrapEvent,hwTrapSeverity,hwTrapServerIdentity, hwTrapLocation, hwTrapTime } 
			STATUS  current
			DESCRIPTION
				"PCIe card  boot disk does not exist deasserted"
			::= { hwPCIeCardEvent 30 }	
		hwPCIeCardDIMMFailure NOTIFICATION-TYPE
			OBJECTS { hwTrapSeq, hwTrapEvent,hwTrapSeverity,hwTrapServerIdentity, hwTrapLocation, hwTrapTime } 
			STATUS  current
			DESCRIPTION
				"PCIe card DIMM is failure"
			::= { hwPCIeCardEvent 31 }
		hwPCIeCardDIMMFailureDeassert NOTIFICATION-TYPE
			OBJECTS { hwTrapSeq, hwTrapEvent,hwTrapSeverity,hwTrapServerIdentity, hwTrapLocation, hwTrapTime } 
			STATUS  current
			DESCRIPTION
				"PCIe card DIMM is failure deasserted"
			::= { hwPCIeCardEvent 32 }	
		hwPCIeCardFWInitFailure NOTIFICATION-TYPE
			OBJECTS { hwTrapSeq, hwTrapEvent,hwTrapSeverity,hwTrapServerIdentity, hwTrapLocation, hwTrapTime } 
			STATUS  current
			DESCRIPTION
				"PCIe card  has a firmware initialization alarm "
			::= { hwPCIeCardEvent 33 }	
		hwPCIeCardFWInitFailureDeassert NOTIFICATION-TYPE
			OBJECTS { hwTrapSeq, hwTrapEvent,hwTrapSeverity,hwTrapServerIdentity, hwTrapLocation, hwTrapTime } 
			STATUS  current
			DESCRIPTION
				"PCIe card  has a firmware initialization alarm deasserted"
			::= { hwPCIeCardEvent 34 }	
		hwPCIeCardCPUInitFailure NOTIFICATION-TYPE
			OBJECTS { hwTrapSeq, hwTrapEvent,hwTrapSeverity,hwTrapServerIdentity, hwTrapLocation, hwTrapTime } 
			STATUS  current
			DESCRIPTION
				"PCIe card  CPU has an initialization alarm"
			::= { hwPCIeCardEvent 35 }
		hwPCIeCardCPUInitFailureDeassert NOTIFICATION-TYPE
			OBJECTS { hwTrapSeq, hwTrapEvent,hwTrapSeverity,hwTrapServerIdentity, hwTrapLocation, hwTrapTime } 
			STATUS  current
			DESCRIPTION
				"PCIe card  CPU has an initialization alarm deasserted"
			::= { hwPCIeCardEvent 36 }
		hwPCIeCardWatchDogTimeout NOTIFICATION-TYPE
			OBJECTS { hwTrapSeq, hwTrapEvent,hwTrapSeverity,hwTrapServerIdentity, hwTrapLocation, hwTrapTime } 
			STATUS  current
			DESCRIPTION
				"PCIe card has a watchdog timeout alarm"
			::= { hwPCIeCardEvent 37 }
		hwPCIeCardWatchDogTimeoutDeassert NOTIFICATION-TYPE
			OBJECTS { hwTrapSeq, hwTrapEvent,hwTrapSeverity,hwTrapServerIdentity, hwTrapLocation, hwTrapTime } 
			STATUS  current
			DESCRIPTION
				"PCIe card has a watchdog timeout alarm deasserted"
			::= { hwPCIeCardEvent 38 }	
		hwPCIeCardBBULowerVoltage NOTIFICATION-TYPE
			OBJECTS { hwTrapSeq, hwTrapEvent,hwTrapSeverity,hwTrapServerIdentity, hwTrapLocation, hwTrapTime } 
			STATUS  current
			DESCRIPTION
				"PCIe card BBU voltage is low"
			::= { hwPCIeCardEvent 57 }
		hwPCIeCardBBULowerVoltageDeassert NOTIFICATION-TYPE
			OBJECTS { hwTrapSeq, hwTrapEvent,hwTrapSeverity,hwTrapServerIdentity, hwTrapLocation, hwTrapTime } 
			STATUS  current
			DESCRIPTION
				"PCIe card BBU voltage is low deasserted"
			::= { hwPCIeCardEvent 58 }
		hwPCIeCardBBUFault NOTIFICATION-TYPE
			OBJECTS { hwTrapSeq, hwTrapEvent,hwTrapSeverity,hwTrapServerIdentity, hwTrapLocation, hwTrapTime } 
			STATUS  current
			DESCRIPTION
				"PCIe card  BBU is fault"
			::= { hwPCIeCardEvent 59 }
		hwPCIeCardBBUFaultDeassert NOTIFICATION-TYPE
			OBJECTS { hwTrapSeq, hwTrapEvent,hwTrapSeverity,hwTrapServerIdentity, hwTrapLocation, hwTrapTime } 
			STATUS  current
			DESCRIPTION
				"PCIe card  BBU is fault deasserted"
			::= { hwPCIeCardEvent 60 }	
		hwPCIeCardBBUNotPresent NOTIFICATION-TYPE
			OBJECTS { hwTrapSeq, hwTrapEvent,hwTrapSeverity,hwTrapServerIdentity, hwTrapLocation, hwTrapTime } 
			STATUS  current
			DESCRIPTION
				 "PCIe card BBU is absent"
			::= { hwPCIeCardEvent 61 }
		hwPCIeCardBBUPresent NOTIFICATION-TYPE
			OBJECTS { hwTrapSeq, hwTrapEvent,hwTrapSeverity,hwTrapServerIdentity, hwTrapLocation, hwTrapTime } 
			STATUS  current
			DESCRIPTION
				"PCIe card BBU is present"
			::= { hwPCIeCardEvent 63 }			

	hwMemoryEvent OBJECT IDENTIFIER ::= {hwServerTRAPObjectV2 2} 
    
    hwMemoryConfigError NOTIFICATION-TYPE
      OBJECTS { hwTrapSeq, hwTrapSensorName, hwTrapEvent, hwTrapSeverity, hwTrapEventCode, hwTrapServerIdentity, hwTrapLocation, hwTrapTime }
      STATUS  current
      DESCRIPTION
              "Memory configuration error"
      ::= { hwMemoryEvent 37 }

    hwMemoryConfigErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory configuration error deassert"
      ::= { hwMemoryEvent 38 }
    
    hwMemoryInitializationError NOTIFICATION-TYPE
      OBJECTS { hwTrapSeq, hwTrapSensorName, hwTrapEvent, hwTrapSeverity, hwTrapEventCode, hwTrapServerIdentity, hwTrapLocation, hwTrapTime }
      STATUS  current
      DESCRIPTION
              "Memory configuration error"
      ::= { hwMemoryEvent 39 }

    hwMemoryInitializationErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory configuration error deassert"
      ::= { hwMemoryEvent 40 }
    
	hwCPUMemoryEvent OBJECT IDENTIFIER ::= {hwServerTRAPObjectV2 45} 
    
    hwNoAvailableMemoryError NOTIFICATION-TYPE
      OBJECTS { hwTrapSeq, hwTrapSensorName, hwTrapEvent, hwTrapSeverity, hwTrapEventCode, hwTrapServerIdentity, hwTrapLocation, hwTrapTime }
      STATUS  current
      DESCRIPTION
              "CPU has no available memory"
      ::= { hwCPUMemoryEvent 79 }
    
    hwNoAvailableMemoryErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU has no available memory deassert"
      ::= { hwCPUMemoryEvent 80 }

    hwCPUMemoryConfigError NOTIFICATION-TYPE
      OBJECTS { hwTrapSeq, hwTrapSensorName, hwTrapEvent, hwTrapSeverity, hwTrapEventCode, hwTrapServerIdentity, hwTrapLocation, hwTrapTime }
      STATUS  current
      DESCRIPTION
              "CPU memory configuration error"
      ::= { hwCPUMemoryEvent 75 }
    
    hwCPUMemoryConfigErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU memory configuration error deassert"
      ::= { hwCPUMemoryEvent 76 }
      
    hwCPUMRCFatalError NOTIFICATION-TYPE
      OBJECTS { hwTrapSeq, hwTrapSensorName, hwTrapEvent, hwTrapSeverity, hwTrapEventCode, hwTrapServerIdentity, hwTrapLocation, hwTrapTime }
      STATUS  current
      DESCRIPTION
              "CPU memory MRC fatal error"
      ::= { hwCPUMemoryEvent 77 }
    
    hwCPUMRCFatalErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "CPU memory MRC fatal error deassert"
      ::= { hwCPUMemoryEvent 78 }

    hwMemoryBoardEvent OBJECT IDENTIFIER ::= {hwServerTRAPObjectV2 15} 
	
	hwMemoryBoardSMI2TainingError NOTIFICATION-TYPE
      OBJECTS { hwTrapSeq, hwTrapSensorName, hwTrapEvent, hwTrapSeverity, hwTrapEventCode, hwTrapServerIdentity, hwTrapLocation, hwTrapTime }
      STATUS  current
      DESCRIPTION
              "Memory board SMI2 training error"
      ::= { hwMemoryBoardEvent 5 }
	
	hwMemoryBoardSMI2TainingErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Memory board SMI2 training error deassert"
      ::= { hwMemoryBoardEvent 6 }
	  
	hwMainboardEvent OBJECT IDENTIFIER ::= {hwServerTRAPObjectV2 17} 
	
	hwMainboardSMI2TainingError NOTIFICATION-TYPE
      OBJECTS { hwTrapSeq, hwTrapSensorName, hwTrapEvent, hwTrapSeverity, hwTrapEventCode, hwTrapServerIdentity, hwTrapLocation, hwTrapTime }
      STATUS  current
      DESCRIPTION
              "Mainboard SMI2 training error"
      ::= { hwMainboardEvent 155 }
	
	hwMainboardSMI2TainingErrorDeassert NOTIFICATION-TYPE
      OBJECTS { hwTrapSeq, hwTrapSensorName, hwTrapEvent, hwTrapSeverity, hwTrapEventCode, hwTrapServerIdentity, hwTrapLocation, hwTrapTime }
      STATUS  current
      DESCRIPTION
              "Mainboard SMI2 training error deassert"
      ::= { hwMainboardEvent 156 }
--    ****** remoteManagement Information *******************************
  
		remoteManagement OBJECT IDENTIFIER ::= { hwiBMC 28 }           
			

		powerOnControl OBJECT-TYPE
			SYNTAX DisplayString
			MAX-ACCESS read-write
			STATUS current
			DESCRIPTION
				"The powerOnControl format: IP,PORT,ENABLE(eg 192.168.1.1,6999,1), maxlength is 255 characters."
			::= { remoteManagement 1 }
			
			
--    ****** SDCard Information *******************************
  
		sdCardProperty OBJECT IDENTIFIER ::= { hwiBMC 32 }
		

		sdCardControllerManufacturer OBJECT-TYPE
			SYNTAX DisplayString 
			MAX-ACCESS read-only
			STATUS current
			DESCRIPTION
				"Information about SD card controller manufacturer."
			::= { sdCardProperty 1 }    
			
		sdCardControllerVersion OBJECT-TYPE
			SYNTAX DisplayString 
			MAX-ACCESS read-only
			STATUS current
			DESCRIPTION
				"Information about SD card controller version."
			::= { sdCardProperty 2 }    

		sdCardEntireStatus OBJECT-TYPE
			SYNTAX INTEGER 
				{
				ok(1),
				minor(2),
				major(3),
				critical(4),
				absence(5),
				unknown(6)
				}
			MAX-ACCESS read-only
			STATUS current
			DESCRIPTION
				"Information about all sdcard health status."
			::= { sdCardProperty 3 }   

		sdCardDescriptionTable OBJECT-TYPE
			SYNTAX SEQUENCE OF SdCardDescriptionEntry 
			MAX-ACCESS not-accessible
			STATUS current
			DESCRIPTION
				"A table containing the sd card."
			::= { sdCardProperty 50 }
        
                sdCardDescriptionEntry OBJECT-TYPE
			SYNTAX SdCardDescriptionEntry 
			MAX-ACCESS not-accessible
			STATUS current
			DESCRIPTION
				"Information about sd card."
			INDEX { sdCardIndex }
			::= { sdCardDescriptionTable 1 }
		
		SdCardDescriptionEntry ::=
			SEQUENCE {
				sdCardIndex
					INTEGER, 
				sdCardPresence
					INTEGER,
				sdCardStatus
					INTEGER,
				sdCardCapacity 
					INTEGER, 
				sdCardManufacturer
					DisplayString,
				sdCardSN
					DisplayString	
				}
				 

		sdCardIndex OBJECT-TYPE	
			SYNTAX INTEGER
			MAX-ACCESS not-accessible
			STATUS current
			DESCRIPTION
				"Information about sd card index."
			::= { sdCardDescriptionEntry 1 } 
			

		sdCardPresence OBJECT-TYPE
			SYNTAX INTEGER
				{
				absence(1),
				presence(2),
				unknown(3)
				}
			MAX-ACCESS read-only
			STATUS current
			DESCRIPTION
				"Information about sd card presence."
			::= { sdCardDescriptionEntry 2 }


		sdCardStatus OBJECT-TYPE
			SYNTAX INTEGER 
				{
				ok(1),
				minor(2),
				major(3),
				critical(4),
				absence(5),
				unknown(6)
				}
			MAX-ACCESS read-only
			STATUS current
			DESCRIPTION
				"Information about sd card health."
			::= { sdCardDescriptionEntry 3 }  

		sdCardCapacity OBJECT-TYPE	
			SYNTAX INTEGER
			MAX-ACCESS read-only
			STATUS current
			DESCRIPTION
				"sd card capacity(MB)."
			::= { sdCardDescriptionEntry 4 } 

		
		sdCardManufacturer OBJECT-TYPE	
			SYNTAX DisplayString
			MAX-ACCESS read-only
			STATUS current
			DESCRIPTION
				"sd card manufacturer."
			::= { sdCardDescriptionEntry 5 } 

		
		sdCardSN OBJECT-TYPE	
			SYNTAX DisplayString
			MAX-ACCESS read-only
			STATUS current
			DESCRIPTION
				"sd card sn."
			::= { sdCardDescriptionEntry 6 } 				

			
--    ****** securityModuleProperty Information *******************************
  
		securityModuleProperty OBJECT IDENTIFIER ::= { hwiBMC 33 }
			

		presence OBJECT-TYPE
			SYNTAX INTEGER
				{
				absence(1),
				presence(2),
				unknown(3)
				}
			MAX-ACCESS read-only
			STATUS current
			DESCRIPTION
				"Presence of security module."
			::= { securityModuleProperty 1 }
			

		specificationType OBJECT-TYPE
			SYNTAX DisplayString
			MAX-ACCESS read-only
			STATUS current
			DESCRIPTION
				"Specification type of security module."
			::= { securityModuleProperty 2 } 
			

		specificationVersion OBJECT-TYPE
			SYNTAX DisplayString
			MAX-ACCESS read-only
			STATUS current
			DESCRIPTION
				"Specification version of security module."
			::= { securityModuleProperty 3 }	
			

		manufacturerName OBJECT-TYPE
			SYNTAX DisplayString
			MAX-ACCESS read-only
			STATUS current
			DESCRIPTION
				"Manufacturer name of security module."
			::= { securityModuleProperty 4 }
			

		manufacturerVersion OBJECT-TYPE
			SYNTAX DisplayString
			MAX-ACCESS read-only
			STATUS current
			DESCRIPTION
				"Manufacturer firmware version of security module."
			::= { securityModuleProperty 5 }
--    ****** fileTransfer Information *******************************
    fileTransfer OBJECT IDENTIFIER ::= { hwiBMC 35 }
	
	fileTransferUrl OBJECT-TYPE
			SYNTAX DisplayString
			MAX-ACCESS read-write
			STATUS current
			DESCRIPTION
				"The file transfer URL format is: <download/upload><ID><protocol://[username:password@]IP[:port]/directory/filename> 
				 The maximum length of the URL is 1024 bytes.
				 The parameters in the URL are described as follows:
				 	 The download means download file to BMC.
				 	 The upload means upload file to the destination server. 
				 	 The ID is the file ID, ranging from 0 to 255.
				 	 The supported protocols include https, sftp, cifs, scp, and nfs.
				 	 The username and password are those of the destination server. 
				 	 The IP can be set to an IPv4/IPv6 address or a domain name.
				 	 The directory and filename are those on the destination server.
				 Example URLs are as follows: 
				 	 download;0;https://root:test1234@192.168.2.13:443/data/display0.ini
				 	 upload;1;sftp://root:test1234@[2001::178]/home/options0.ini
				 The URL can contain only letters, digits, and special characters. The directory or file name cannot contain @."
			::= { fileTransfer 1 }                                                                                                                           
	
	fileTransferState OBJECT-TYPE
			SYNTAX INTEGER
			MAX-ACCESS read-only
			STATUS current
			DESCRIPTION
				"Information about file transfer state.
				the value defined as:
				  -1  : unknown error,
				  -101: download unavailable,
				  -102: file name too long,
				  -103: file length out of MAXlength or out of memory,
				  -104: set file update flag error,
				  -105: libcurl run error,
				  -106: upload unavailable,
				  -107: upload file unavailable,
				  -108: protocol not supported,
				  -109: url format error,
				  [0,100]:represents transfer progress in percentage while file being transfered."
			::= { fileTransfer 2 } 
      			                                                     
		                                       
--    ****** RAID Controller Information *******************************
  
		raidControllerProperty OBJECT IDENTIFIER ::= { hwiBMC 36 } 

		raidControllerDescriptionTable OBJECT-TYPE
			SYNTAX SEQUENCE OF RAIDControllerDescriptionEntry 
			MAX-ACCESS not-accessible
			STATUS current
			DESCRIPTION
				"A table containing the RAID controller."
			::= { raidControllerProperty 50 }
        
                raidControllerDescriptionEntry OBJECT-TYPE
			SYNTAX RAIDControllerDescriptionEntry 
			MAX-ACCESS not-accessible
			STATUS current
			DESCRIPTION
				"Information about RAID controller."
			INDEX { raidControllerIndex }
			::= { raidControllerDescriptionTable 1 }
		
		RAIDControllerDescriptionEntry ::=
			SEQUENCE {
				raidControllerIndex
					INTEGER, 
				raidControllerName
					DisplayString,
				raidControllerType
					DisplayString,
				raidControllerComponentName
					DisplayString, 
				raidControllerSupportOOBManagement
					INTEGER,
				raidControllerMode
					INTEGER,
				raidControllerHealthStatus
					INTEGER,	
				raidControllerFwVersion
					DisplayString,	
				raidControllerNVDataVersion
					DisplayString,
				raidControllerMemorySizeInMB
					INTEGER,
				raidControllerDeviceInterface
					INTEGER,
				raidControllerSASAddress
					DisplayString,
				raidControllerCachePinned
					INTEGER,
				raidControllerMaintainPDFailHistory
					INTEGER,
				raidControllerDDREccCount
					INTEGER,
				raidControllerBBUPresence
					INTEGER,
				raidControllerBBUType
					DisplayString,
				raidControllerBBUHealthStatus
					INTEGER,
				raidControllerMinStripSupportInBytes
					INTEGER,
				raidControllerMaxStripSupportInBytes
					INTEGER,
				raidControllerCopybackEnable
					INTEGER,
				raidControllerSMARTerCopybackEnable
					INTEGER,
				raidControllerJBODEnable
					INTEGER,					
				raidControllerRestoreSettings
					INTEGER,	
				raidControllerCreateLD
					DisplayString,	
				raidControllerAddLD
					DisplayString,						
				}											   

		raidControllerIndex OBJECT-TYPE
			SYNTAX INTEGER
			MAX-ACCESS not-accessible
			STATUS current
			DESCRIPTION
				"Information about RAID controller index."
			::= { raidControllerDescriptionEntry 1 }

		raidControllerName OBJECT-TYPE
			SYNTAX DisplayString
			MAX-ACCESS read-only
			STATUS current
			DESCRIPTION
				"Information about RAID controller name."
			::= { raidControllerDescriptionEntry 2 }				
											   											   
		raidControllerType OBJECT-TYPE
			SYNTAX DisplayString
			MAX-ACCESS read-only
			STATUS current
			DESCRIPTION
				"Information about RAID controller type."
			::= { raidControllerDescriptionEntry 3 }

		raidControllerComponentName OBJECT-TYPE
			SYNTAX DisplayString
			MAX-ACCESS read-only
			STATUS current
			DESCRIPTION
				"Information about RAID controller component name."
			::= { raidControllerDescriptionEntry 4 }

		raidControllerSupportOOBManagement OBJECT-TYPE
			SYNTAX INTEGER
				{
				no(1),
				yes(2)
				}
			MAX-ACCESS read-only
			STATUS current
			DESCRIPTION
				"Information about RAID controller if support OOB management.
				1: No
				2: Yes"
			::= { raidControllerDescriptionEntry 5 }
			
		raidControllerMode OBJECT-TYPE
			SYNTAX INTEGER
				{
				none-raid(1),
				raid(2),
				unknown(255)
				}
			MAX-ACCESS read-only
			STATUS current
			DESCRIPTION
				"Information about RAID controller mode.
				1: None-RAID
				2: RAID
				255: Unknown"
			::= { raidControllerDescriptionEntry 6 }

		raidControllerHealthStatus OBJECT-TYPE
			SYNTAX INTEGER
				{
				unknown(65535)
				}			
			MAX-ACCESS read-only
			STATUS current
			DESCRIPTION
				"Information about RAID controller health status.
				bit0: 1- memory correctable error
				bit1: 1- memory uncorrectable error
				bit2: 1- memory ECC error reached limit
				bit3: 1- NVRAM uncorrectable error
				other: reserved"
			::= { raidControllerDescriptionEntry 7 }

		raidControllerFwVersion OBJECT-TYPE
			SYNTAX DisplayString
			MAX-ACCESS read-only
			STATUS current
			DESCRIPTION
				"Information about RAID controller firmware version."
			::= { raidControllerDescriptionEntry 8 }
		
		raidControllerNVDataVersion OBJECT-TYPE
			SYNTAX DisplayString
			MAX-ACCESS read-only
			STATUS current
			DESCRIPTION
				"Information about RAID controller NVData version."
			::= { raidControllerDescriptionEntry 9 }

		raidControllerMemorySizeInMB OBJECT-TYPE
			SYNTAX INTEGER
				{
				unknown(65535)
				}			
			MAX-ACCESS read-only
			STATUS current
			DESCRIPTION
				"Information about RAID controller memory size (MB)."
			::= { raidControllerDescriptionEntry 10 }			

		raidControllerDeviceInterface OBJECT-TYPE
			SYNTAX INTEGER
				{
				spi(1),
				sas-3G(2),
				sata-1-5G(3),
				sata-3G(4),
				sas-6G(5),
				sas-12G(6),
				unknown(255)
				}			
			MAX-ACCESS read-only
			STATUS current
			DESCRIPTION
				"Information about RAID controller device interface type.
				1: SPI
				2: SAS-3G
				3: SATA-1.5G
				4: SATA-3G
				5: SAS-6G
				6: SAS-12G
				255: Unknown"
			::= { raidControllerDescriptionEntry 11 }				

		raidControllerSASAddress OBJECT-TYPE
			SYNTAX DisplayString
			MAX-ACCESS read-only
			STATUS current
			DESCRIPTION
				"Information about RAID controller SAS address."
			::= { raidControllerDescriptionEntry 12 }

		raidControllerCachePinned OBJECT-TYPE
			SYNTAX INTEGER
				{
				no(1),
				yes(2),
				unknown(255)
				}			
			MAX-ACCESS read-only
			STATUS current
			DESCRIPTION
				"Information about RAID controller if cache is pinned.
				1: No
				2: Yes
				255: Unknown"
			::= { raidControllerDescriptionEntry 13 }				
			
		raidControllerMaintainPDFailHistory OBJECT-TYPE
			SYNTAX INTEGER
				{
				no(1),
				yes(2),
				unknown(255)
				}			
			MAX-ACCESS read-only
			STATUS current
			DESCRIPTION
				"Information about RAID controller if maintain PD fail history.
				1: No
				2: Yes
				255: Unknown"
			::= { raidControllerDescriptionEntry 14 }

		raidControllerDDREccCount OBJECT-TYPE
			SYNTAX INTEGER
				{
				unknown(65535)
				}			
			MAX-ACCESS read-only
			STATUS current
			DESCRIPTION
				"Information about RAID controller DDR ECC count."
			::= { raidControllerDescriptionEntry 15 }

		raidControllerBBUPresence OBJECT-TYPE
			SYNTAX INTEGER
				{
				absent(1),
				present(2),
				unknown(255)
				}			
			MAX-ACCESS read-only
			STATUS current
			DESCRIPTION
				"Information about RAID controller's BBU presence.
				1: Absent
				2: Present
				255: Unknown"
			::= { raidControllerDescriptionEntry 16 }

		raidControllerBBUType OBJECT-TYPE
			SYNTAX DisplayString
			MAX-ACCESS read-only
			STATUS current
			DESCRIPTION
				"Information about RAID controller' BBU type."
			::= { raidControllerDescriptionEntry 17 }			
			
		raidControllerBBUHealthStatus OBJECT-TYPE
			SYNTAX INTEGER			
			MAX-ACCESS read-only
			STATUS current
			DESCRIPTION
				"Information about RAID controller's BBU health status.
				bit0: 1 - voltage is low
				bit1: 1 - need replace pack
				bit2: 1 - learn cycle failed
				bit3: 1 - learn cycle timeout
				bit4: 1 - pack is about to fail
				bit5: 1 - remaining capacity low
				bit6: 1 - no space for cache offload
				others: reserved"
			::= { raidControllerDescriptionEntry 18 }
			
		raidControllerMinStripSupportInBytes OBJECT-TYPE
			SYNTAX INTEGER
			{
				unknown(-1)
			}			
			MAX-ACCESS read-only
			STATUS current
			DESCRIPTION
				"Information about the minimum strip size that RAID controller support."
			::= { raidControllerDescriptionEntry 19 }
			
		raidControllerMaxStripSupportInBytes OBJECT-TYPE
			SYNTAX INTEGER
			{
				unknown(-1)
			}			
			MAX-ACCESS read-only
			STATUS current
			DESCRIPTION
				"Information about the maximum strip size that RAID controller support."
			::= { raidControllerDescriptionEntry 20 }			
			
		raidControllerCopybackEnable OBJECT-TYPE
			SYNTAX INTEGER
				{
				unknown(1),
				disabled(2),
				enabled(3)
				}			
			MAX-ACCESS read-write
			STATUS current
			DESCRIPTION
				"Information about the copyback state of RAID controller.
				1: Unknown (read only)
				2: Disabled
				3: Enabled"
			::= { raidControllerDescriptionEntry 21 }			
			
		raidControllerSMARTerCopybackEnable OBJECT-TYPE
			SYNTAX INTEGER
				{
				unknown(1),
				disabled(2),
				enabled(3)
				}			
			MAX-ACCESS read-write
			STATUS current
			DESCRIPTION
				"Information about the copyback state on SMART error of RAID controller.
				1: Unknown (read only)
				2: Disabled
				3: Enabled
				
				Note: Set action is available only when raidControllerCopybackEnable = Enabled."
			::= { raidControllerDescriptionEntry 22 }			
			                                                 
		raidControllerJBODEnable OBJECT-TYPE
			SYNTAX INTEGER
				{
				unknown(1),
				disabled(2),
				enabled(3)
				}			
			MAX-ACCESS read-write
			STATUS current
			DESCRIPTION
				"Information about the JBOD state of RAID controller.
				1: Unknown (read only)
				2: Disabled
				3: Enabled"
			::= { raidControllerDescriptionEntry 23 }			
			
		raidControllerRestoreSettings OBJECT-TYPE
			SYNTAX INTEGER			
			MAX-ACCESS read-write
			STATUS current
			DESCRIPTION
				"Restore RAID controller settings (write only). The argument is:
				1: Restore RAID controller settings.
				others: invalid"
			::= { raidControllerDescriptionEntry 24 }			
			
		raidControllerCreateLD OBJECT-TYPE
			SYNTAX DisplayString			
			MAX-ACCESS read-write
			STATUS current
			DESCRIPTION
				"Create new logical drive on this RAID controller. The arguments are seperated by semicolons;
				The arguments format is <option1>=<argument>;<option2>=<argument>;...;<optionN>=<argument>;
				example: 
					rl=r1;pd=1,2;name=example;size=100.375g;ss=256k;sc=1;rp=ra;wp=wb;iop=cio;ap=rw;dcp=enabled;init=quick;
				or  
					rl=r50;pd=1,2,3,4,5,6,7,8,9;name=example;size=500g;ss=1M;sc=3;rp=ra;wp=wb;iop=cio;ap=rw;dcp=enabled;init=quick;

				Options and arguments:	
				rl=<RAID level>                          The RAID level of logical drive. It is mandatory. When 'cachecade=1' is specified, RAID level 0/1 is valid.
					r0: RAID0
					r1: RAID1
					r5: RAID5
					r6: RAID6
					r10: RAID10
					r50: RAID50
					r60: RAID60
				pd=<PD IDs>                              The physical drives IDs which participate this logical drive. It is mandatory. 
				name=<Logical drive name>                The name of logical drive. The maximum is 15 printable ASCII characters except ';'. It is optional.
				size=<Logical drive size>                The size of logical drive and unit can be 'm'(megabytes),'g'(gigabytes), or 't'(terabytes). 
				                                         It is optional and not necessary when 'cachecade=1' is specified.
				ss=<Logical drive strip size>            The strip size of logical drive. The valid values are 64k,128k,256k,512k,1M. 
				                                         It is optional and not necessary when 'cachecade=1' is specified.
				sc=<Span count>                          The span count of logical drive. The default is 1 when RAID level is RAID0/1/5/6 and 2 when RAID level is RAID10/50/60. 
				                                         It is optional and not necessary when 'cachecade=1' is specified.
				rp=<Read Policy>                         The read policy of logical drive. It is optional and not necessary when 'cachecade=1' is specified.
					ra: Read Ahead
					nra: No Read Ahead
				wp=<Write Policy>                        The write policy of logical drive. It is optional.
					wt: Write Through
					wbwithbbu: Write Back with BBU
					wb: Write Back
				iop=<IO Policy>                          The IO policy of logical drive. It is optional and not necessary when 'cachecade=1' is specified.
					cio: Cached IO
					dio: Direct IO
				ap=<Access Policy>                       The access policy of logical drive. It is optional and not necessary when 'cachecade=1' is specified.
					rw: Read Write
					ro: Read only
					blocked: Blocked
				dcp=<Disk Cache Policy>                  The disk cache policy of logical drive. It is optional and not necessary when 'cachecade=1' is specified.
					enabled: Enable disk cache
					disabled: Disable disk cache
					default: Unchanged(Disk's default)
				init=<Init Type>                         The initialization type of logical drive. It is optional and not necessary when 'cachecade=1' is specified.
					no: No init
					quick: Quick init
					full: Full init
				cachecade=1                              Logical drive is used for secondary cache. It is optional. It must be supported by RAID controller first.
				
				Note: Character ';' is not valid for logical drive name string because it is used as separator."
			::= { raidControllerDescriptionEntry 25 }			
			
		raidControllerAddLD OBJECT-TYPE
			SYNTAX DisplayString			
			MAX-ACCESS read-write
			STATUS current
			DESCRIPTION
				"Add logical drive on array on this RAID controller. The arguments are seperated by semicolons;
				The arguments format is <option1>=<argument>;<option2>=<argument>;...;<optionN>=<argument>;
				example: 
					array=1;name=example;size=100.375g;ss=512k;rp=ra;wp=wb;iop=cio;ap=rw;dcp=enabled;init=quick;

				Options and arguments:	
				array=<Array ID>                          The array on which the logical drive will be added. It is mandatory.
				name=<Logical drive name>                 The name of logical drive and maximum is 15 printable ASCII characters except ';'. It is optional.
				size=<Logical drive size>                 The size of logical drive and unit can be 'm'(megabytes),'g'(gigabytes), or 't'(terabytes). It is optional.
				ss=<Logical drive strip size>             The strip size of logical drive. The valid values are 64k,128k,256k,512k,1M. It is optional.
				rp=<Read Policy>                          The read policy of logical drive. It is optional.
					ra: Read Ahead
					nra: No Read Ahead
				wp=<Write Policy>                         The write policy of logical drive. It is optional.
					wt: Write Through
					wbwithbbu: Write Back with BBU
					wb: Write Back
				iop=<IO Policy>                           The IO policy of logical drive. It is optional.
					cio: Cached IO
					dio: Direct IO
				ap=<Access Policy>                        The access policy of logical drive. It is optional.
					rw: Read Write
					ro: Read only
					blocked: Blocked
				dcp=<Disk Cache Policy>                   The disk cache policy of logical drive. It is optional.
					enabled: Enable disk cache
					disabled: Disable disk cache
					default: Unchanged(Disk's default)
				init=<Init Type>                          The initialization type of logical drive. It is optional.
					no: No init
					quick: Quick init
					full: Full init
					
				Note: Character ';' is not valid for logical drive name string because it is used as separator."
			::= { raidControllerDescriptionEntry 26 }			
			
--  ****************** Logical Drive information **********************

		logicalDriveProperty OBJECT IDENTIFIER ::= { hwiBMC 37 } 

		logicalDriveDescriptionTable OBJECT-TYPE
			SYNTAX SEQUENCE OF LogicalDriveDescriptionEntry 
			MAX-ACCESS not-accessible
			STATUS current
			DESCRIPTION
				"A table containing the logical drive created by RAID controller."
			::= { logicalDriveProperty 50 }
        
                logicalDriveDescriptionEntry OBJECT-TYPE
			SYNTAX LogicalDriveDescriptionEntry 
			MAX-ACCESS not-accessible
			STATUS current
			DESCRIPTION
				"Information about logical drive."
			INDEX { logicalDriveRAIDControllerIndex, logicalDriveIndex }
			::= { logicalDriveDescriptionTable 1 }
		
		LogicalDriveDescriptionEntry ::=
			SEQUENCE {
				logicalDriveRAIDControllerIndex
					INTEGER,
				logicalDriveIndex
					INTEGER,					
				logicalDriveRAIDLevel
					DisplayString,
				logicalDriveState
					INTEGER,
				logicalDriveDefaultReadPolicy
					INTEGER, 
				logicalDriveDefaultWritePolicy
					INTEGER,
				logicalDriveDefaultIOPolicy
					INTEGER,
				logicalDriveCurrentReadPolicy
					INTEGER,	
				logicalDriveCurrentWritePolicy
					INTEGER,	
				logicalDriveCurrentIOPolicy
					INTEGER,
				logicalDriveSpanDepth
					INTEGER,
				logicalDriveNumDrivePerSpan
					INTEGER,
				logicalDriveStripeSizeInBytes
					INTEGER,
				logicalDriveStripeSizeInMB
					INTEGER,					
				logicalDriveSizeInMB
					INTEGER,
				logicalDriveDiskCachePolicy
					INTEGER,
				logicalDriveConsistencyCheckStatus
					INTEGER,
				logicalDriveBootable
					INTEGER,
				logicalDriveName
					DisplayString,
				logicalDriveAccessPolicy
					INTEGER,
				logicalDriveInitState
					INTEGER,	
				logicalDriveBGIEnable
					INTEGER,	
				logicalDriveIsSSCD
					INTEGER,	
				logicalDriveSSCDCachingEnable
					INTEGER,	
				logicalDriveAssociatedLDs
					DisplayString,
				logicalDriveDedicatedSparePD
					DisplayString,	
				logicalDriveDelete
					INTEGER,					
				}											   

		logicalDriveRAIDControllerIndex OBJECT-TYPE
			SYNTAX INTEGER
			MAX-ACCESS not-accessible
			STATUS current
			DESCRIPTION
				"Information about RAID controller index to which this logical drive belongs."
			::= { logicalDriveDescriptionEntry 1 }			

		logicalDriveIndex OBJECT-TYPE
			SYNTAX INTEGER
			MAX-ACCESS not-accessible
			STATUS current
			DESCRIPTION
				"Information about logical drive index in current RAID controller."
			::= { logicalDriveDescriptionEntry 2 }			
			
		logicalDriveRAIDLevel OBJECT-TYPE
			SYNTAX DisplayString			
			MAX-ACCESS read-only
			STATUS current
			DESCRIPTION
				"Information about logical drive RAID level."
			::= { logicalDriveDescriptionEntry 3 }				
											   											   
		logicalDriveState OBJECT-TYPE
			SYNTAX INTEGER
			{
				offline(1),
				partial-degraded(2),
				degraded(3),
				optimal(4),
				unknown(255)
			}
			MAX-ACCESS read-only
			STATUS current
			DESCRIPTION
				"Information about logical drive state.
				1: Offline
				2: Partial degraded
				3: Degraded
				4: Optimal
				255: Unknown"
			::= { logicalDriveDescriptionEntry 4 }

		logicalDriveDefaultReadPolicy OBJECT-TYPE
			SYNTAX INTEGER
			{
				no-read-ahead(1),
				read-ahead(2),
				unknown(255)
			}
			MAX-ACCESS read-write
			STATUS current
			DESCRIPTION
				"Information about logical drive default read policy.
				1: No read ahead
				2: Read ahead
				255: Unknown (read only)
				
				Note: Set action is not available when logical drive is used for secondary cache(logicalDriveIsSSCD = Yes)."
			::= { logicalDriveDescriptionEntry 5 }

		logicalDriveDefaultWritePolicy OBJECT-TYPE
			SYNTAX INTEGER
			{
				write-through(1),
				write-back-with-bbu(2),
				write-back(3),
				unknown(255)
			}
			MAX-ACCESS read-write
			STATUS current
			DESCRIPTION
				"Information about logical drive default write policy.
				1: Write through
				2: Write back with BBU
				3: Write back
				   This option value is not settable when logical drive is used for secondary cache(logicalDriveIsSSCD = Yes).
				255: Unknown (read only)"
			::= { logicalDriveDescriptionEntry 6 }
			
		logicalDriveDefaultIOPolicy OBJECT-TYPE
			SYNTAX INTEGER
			{
				cached-IO(1),
				direct-IO(2),
				unknown(255)
			}
			MAX-ACCESS read-write
			STATUS current
			DESCRIPTION
				"Information about logical drive default IO policy.
				1: Cached IO
				2: Direct IO
				255: Unknown (read only)
				
				Note: Set action is not available when logical drive is used for secondary cache(logicalDriveIsSSCD = Yes)."
			::= { logicalDriveDescriptionEntry 7 }

		logicalDriveCurrentReadPolicy OBJECT-TYPE
			SYNTAX INTEGER
			{
				no-read-ahead(1),
				read-ahead(2),
				unknown(255)
			}			
			MAX-ACCESS read-only
			STATUS current
			DESCRIPTION
				"Information about logical drive current read policy.
				1: No read ahead
				2: Read ahead
				255: Unknown"
			::= { logicalDriveDescriptionEntry 8 }

		logicalDriveCurrentWritePolicy OBJECT-TYPE
			SYNTAX INTEGER
			{
				write-through(1),
				write-back-with-bbu(2),
				write-back(3),
				unknown(255)
			}
			MAX-ACCESS read-only
			STATUS current
			DESCRIPTION
				"Information about logical drive current write policy.
				1: Write Through
				2: Write Back with BBU
				3: Write Back
				255: Unknown"
			::= { logicalDriveDescriptionEntry 9 }
		
		logicalDriveCurrentIOPolicy OBJECT-TYPE
			SYNTAX INTEGER
			{
				cached-IO(1),
				direct-IO(2),
				unknown(255)
			}
			MAX-ACCESS read-only
			STATUS current
			DESCRIPTION
				"Information about logical drive current IO policy.
				1: Cached IO
				2: Direct IO
				255: Unknown"
			::= { logicalDriveDescriptionEntry 10 }

		logicalDriveSpanDepth OBJECT-TYPE
			SYNTAX INTEGER
			{
				unknown(255)
			}			
			MAX-ACCESS read-only
			STATUS current
			DESCRIPTION
				"Information about logical drive span depth."
			::= { logicalDriveDescriptionEntry 11 }			

		logicalDriveNumDrivePerSpan OBJECT-TYPE
			SYNTAX INTEGER
			{
				unknown(255)
			}			
			MAX-ACCESS read-only
			STATUS current
			DESCRIPTION
				"Information about logical drive number of drives per span."
			::= { logicalDriveDescriptionEntry 12 }				

		logicalDriveStripeSizeInBytes OBJECT-TYPE
			SYNTAX INTEGER
			{			
				unknown(4294967295)
			}
			MAX-ACCESS read-only
			STATUS current
			DESCRIPTION
				"Information about logical drive stripe size in bytes."
			::= { logicalDriveDescriptionEntry 13 }
			
		logicalDriveStripeSizeInMB OBJECT-TYPE
			SYNTAX INTEGER
			{			
				unknown(4294967295)
			}
			MAX-ACCESS read-only
			STATUS current
			DESCRIPTION
				"Information about logical drive stripe size in mega-bytes."
			::= { logicalDriveDescriptionEntry 14 }			
			

		logicalDriveSizeInMB OBJECT-TYPE
			SYNTAX INTEGER
			{
				unknown(4294967295)
			}			
			MAX-ACCESS read-only
			STATUS current
			DESCRIPTION
				"Information about logical drive size (MB)."
			::= { logicalDriveDescriptionEntry 15 }				
			
		logicalDriveDiskCachePolicy OBJECT-TYPE
			SYNTAX INTEGER
			{
				disk-default(1),
				enabled(2),
				disabled(3),
				unknown(255)
			}			
			MAX-ACCESS read-write
			STATUS current
			DESCRIPTION
				"Information about logical drive disk cache policy.
				1: Disk's default
				2: Enabled
				3: Disabled
				255: Unknown (read only)
				
				Note: Set action is not available when logical drive's participated physical drives are SSD."
			::= { logicalDriveDescriptionEntry 16 }

		logicalDriveConsistencyCheckStatus OBJECT-TYPE
			SYNTAX INTEGER
			{
				stopped(1),
				in-progress(2),
				unknown(255)
			}			
			MAX-ACCESS read-only
			STATUS current
			DESCRIPTION
				"Information about logical drive consistency check status.
				1: Stopped
				2: In-progress
				255: Unknown"
			::= { logicalDriveDescriptionEntry 17 }

		logicalDriveBootable OBJECT-TYPE
			SYNTAX INTEGER
			{
				no(1),
				yes(2),
				unknown(255)
			}			
			MAX-ACCESS read-write
			STATUS current
			DESCRIPTION
				"Information about logical drive if it is bootable.
				1: No (read only)
				2: Yes
				255: Unknown (read only)
				
				Note: 1. CacheCade logical drive can't be set as bootable drive.
				      2. Noraml logical drive(not cachecade) during offline state can be set bootable successfully, but readback value of logicalDriveBootable
				         is still 'No' unless change the logical drive state to online."
			::= { logicalDriveDescriptionEntry 18 }
		
		logicalDriveName OBJECT-TYPE
			SYNTAX DisplayString			
			MAX-ACCESS read-write
			STATUS current
			DESCRIPTION
				"Information about logical drive name. The maximum is 15 printable ASCII characters."
			::= { logicalDriveDescriptionEntry 19 }		
		
		logicalDriveAccessPolicy OBJECT-TYPE
			SYNTAX INTEGER
			{
				unknown(1),			
				read-write(2),
				read-only(3),
				blocked(4),
				hidden(5)
			}			
			MAX-ACCESS read-write
			STATUS current
			DESCRIPTION
				"Information about logical drive access policy.
				1: Unknown (read only)
				2: Read Write
				3: Read Only
				4: Blocked
				5: Hidden (read only)
				
				Note: Set action is not available when logical drive is used for secondary cache(logicalDriveIsSSCD = Yes)."
			::= { logicalDriveDescriptionEntry 20 }		

		logicalDriveInitState OBJECT-TYPE
			SYNTAX INTEGER
			{
				unknown(1),			
				no-init(2),
				quick-init(3),
				full-init(4)
			}			
			MAX-ACCESS read-only
			STATUS current
			DESCRIPTION
				"Information about logical drive init state.
				1: Unknown
				2: No Init
				3: Quick Init
				4: Full Init"
			::= { logicalDriveDescriptionEntry 21 }	
			
		logicalDriveBGIEnable OBJECT-TYPE
			SYNTAX INTEGER
			{
				unknown(1),			
				disabled(2),
				enabled(3)
			}			
			MAX-ACCESS read-write
			STATUS current
			DESCRIPTION
				"Information about logical drive BGI state.
				1: Unknown (read only)
				2: Disabled
				3: Enabled
				
				Note: Set action is not available when logical drive is used for secondary cache(logicalDriveIsSSCD = Yes)."
			::= { logicalDriveDescriptionEntry 22 }	

		logicalDriveIsSSCD OBJECT-TYPE
			SYNTAX INTEGER
			{
				unknown(1),			
				no(2),
				yes(3)
			}			
			MAX-ACCESS read-only
			STATUS current
			DESCRIPTION
				"Information about logical drive if it is used for secondary cache.
				1: Unknown
				2: No
				3: Yes"
			::= { logicalDriveDescriptionEntry 23 }	
			
		logicalDriveSSCDCachingEnable OBJECT-TYPE
			SYNTAX INTEGER
			{
				unknown(1),			
				disabled(2),
				enabled(3)
			}			
			MAX-ACCESS read-write
			STATUS current
			DESCRIPTION
				"Information about logical drive SSCD caching state if it is not used for secondary cache and 
				it's participated physical drives are not SSD.
				1: Unknown (read only)
				2: Disabled
				3: Enabled"
			::= { logicalDriveDescriptionEntry 24 }	
			
		logicalDriveAssociatedLDs OBJECT-TYPE
			SYNTAX DisplayString			
			MAX-ACCESS read-only
			STATUS current
			DESCRIPTION
				"Information about logical drive associated logical drives IDs seperated by commas if it is used for secondary cache."
			::= { logicalDriveDescriptionEntry 25 }	
							
		logicalDriveDedicatedSparePD OBJECT-TYPE
			SYNTAX DisplayString			
			MAX-ACCESS read-only
			STATUS current
			DESCRIPTION
				"Information about logical drive dedicated hot spare physical drives IDs seperated by commas."
			::= { logicalDriveDescriptionEntry 26 }	
							
		logicalDriveDelete OBJECT-TYPE
			SYNTAX INTEGER			
			MAX-ACCESS read-write
			STATUS current
			DESCRIPTION
				"Delete logical drive (write only). The argument is :
				1: delete
				others: invalid"
			::= { logicalDriveDescriptionEntry 27 }	
		
--  ****************** Disk Array information **********************

		diskArrayProperty OBJECT IDENTIFIER ::= { hwiBMC 39 } 

		diskArrayDescriptionTable OBJECT-TYPE
			SYNTAX SEQUENCE OF DiskArrayDescriptionEntry 
			MAX-ACCESS not-accessible
			STATUS current
			DESCRIPTION
				"A table containing the disk array managed by RAID controller."
			::= { diskArrayProperty 50 }
        
                diskArrayDescriptionEntry OBJECT-TYPE
			SYNTAX DiskArrayDescriptionEntry 
			MAX-ACCESS not-accessible
			STATUS current
			DESCRIPTION
				"Information about logical drive."
			INDEX { diskArrayRAIDControllerIndex, diskArrayIndex }
			::= { diskArrayDescriptionTable 1 }
		
		DiskArrayDescriptionEntry ::=
			SEQUENCE {
				diskArrayRAIDControllerIndex
					INTEGER,
				diskArrayIndex
					INTEGER,					
				diskArrayUsedSpaceInMB
					INTEGER,
				diskArrayFreeSpaceInMB
					INTEGER,
				diskArrayLDCount
					INTEGER, 
				diskArrayLDId
					DisplayString,
				diskArrayPDCount
					INTEGER,
				diskArrayPDId
					DisplayString,
				}	

		diskArrayRAIDControllerIndex OBJECT-TYPE
			SYNTAX INTEGER
			MAX-ACCESS not-accessible
			STATUS current
			DESCRIPTION
				"Information about RAID controller index to which this disk array belongs."
			::= { diskArrayDescriptionEntry 1 }			

		diskArrayIndex OBJECT-TYPE
			SYNTAX INTEGER
			MAX-ACCESS not-accessible
			STATUS current
			DESCRIPTION
				"Information about disk array index in current RAID controller."
			::= { diskArrayDescriptionEntry 2 }			
			
		diskArrayUsedSpaceInMB OBJECT-TYPE
			SYNTAX INTEGER
			{
				unknown(4294967295)
			}
			MAX-ACCESS read-only
			STATUS current
			DESCRIPTION
				"Information about the used space in MB of disk array."
			::= { diskArrayDescriptionEntry 3 }				
											   											   
		diskArrayFreeSpaceInMB OBJECT-TYPE
			SYNTAX INTEGER
			{
				unknown(4294967295)
			}
			MAX-ACCESS read-only
			STATUS current
			DESCRIPTION
				"Information about the free space in MB of disk array."
			::= { diskArrayDescriptionEntry 4 }

		diskArrayLDCount OBJECT-TYPE
			SYNTAX INTEGER
			{
				unknown(255)
			}
			MAX-ACCESS read-only
			STATUS current
			DESCRIPTION
				"Information about logical drive count in the disk array."
			::= { diskArrayDescriptionEntry 5 }
				
		diskArrayLDId OBJECT-TYPE
			SYNTAX DisplayString
			MAX-ACCESS read-only
			STATUS current
			DESCRIPTION
				"Information about logical drive IDs in the disk array, seperated by commas."
			::= { diskArrayDescriptionEntry 6 }

		diskArrayPDCount OBJECT-TYPE
			SYNTAX INTEGER
			{
				unknown(255)
			}			
			MAX-ACCESS read-only
			STATUS current
			DESCRIPTION
				"Information about physical drive count in the disk array."
			::= { diskArrayDescriptionEntry 7 }
				
		diskArrayPDId OBJECT-TYPE
			SYNTAX DisplayString
			MAX-ACCESS read-only
			STATUS current
			DESCRIPTION
				"Information about physical drive IDs in the disk array, seperated by commas."
			::= { diskArrayDescriptionEntry 8 }		

--    ****** remoteControl Information *******************************

		remoteControl OBJECT IDENTIFIER ::= { hwiBMC 40 }

		localKVMState OBJECT-TYPE
			SYNTAX INTEGER
			{
				disable(1),
				enable(2)
			}
			MAX-ACCESS read-write
			STATUS current
			DESCRIPTION
				"Local KVM display state. disable 1, enable 2.
				Default value is enable(2)."
			::= { remoteControl 1 }

--    ****** two-factor authentication Location *******************************

		twoFactorAuthentication  OBJECT IDENTIFIER ::= { hwiBMC 41 }

  		twoFactorAuthenticationEnable OBJECT-TYPE
			SYNTAX INTEGER
					{
					disable (1),
					enable (2)
					}
			MAX-ACCESS read-write
			STATUS current
			DESCRIPTION
				"The enable state of two-factor authentication.
				disable 1, enable 2.
				Default value is disable(1)."
			::= { twoFactorAuthentication 1 }

		twoFactorAuthenticationRevocationCheck OBJECT-TYPE
			SYNTAX INTEGER
			{
			disable (1),
			enable (2)
			}

			MAX-ACCESS read-write
			STATUS current
			DESCRIPTION
				"The enable state of certificate revocation check.
				disable 1, enable 2.
				Default value is disable(1)."
			::= { twoFactorAuthentication 2 }

		--root certificate
		rootCertificateDescriptionTable OBJECT-TYPE
			SYNTAX SEQUENCE OF RootCertificateDescriptionEntry
			MAX-ACCESS not-accessible
			STATUS current
			DESCRIPTION
				"A table containing the list of root certificate information."
			::= { twoFactorAuthentication 50 }

		rootCertificateDescriptionEntry OBJECT-TYPE
			SYNTAX RootCertificateDescriptionEntry
			MAX-ACCESS not-accessible
			STATUS current
			DESCRIPTION
				"Information about root certificate."
			INDEX { rootCertificateIndex }
			::= { rootCertificateDescriptionTable 1 }

		RootCertificateDescriptionEntry ::=
			SEQUENCE {
				rootCertificateIndex
					INTEGER,
				rootCertificateIssuedTo
					DisplayString,
				rootCertificateIssuedBy
					DisplayString,
				rootCertificateValidFrom
					DisplayString,
				rootCertificateValidTo
					DisplayString,
				rootCertificateSerialNumber
					DisplayString,
				rootCertificateImport
					DisplayString,
				rootCertificateDelete
					INTEGER
				}

		rootCertificateIndex OBJECT-TYPE
			SYNTAX INTEGER
			MAX-ACCESS not-accessible
			STATUS current
			DESCRIPTION
				""
			::= { rootCertificateDescriptionEntry 1 }

		rootCertificateIssuedTo OBJECT-TYPE
			SYNTAX DisplayString
			MAX-ACCESS read-only
			STATUS current
			DESCRIPTION
				"root certificate subject."
			::= { rootCertificateDescriptionEntry 2 }

		rootCertificateIssuedBy OBJECT-TYPE
			SYNTAX DisplayString
			MAX-ACCESS read-only
			STATUS current
			DESCRIPTION
				"root certificate issuer."
			::= { rootCertificateDescriptionEntry 3 }

		rootCertificateValidFrom OBJECT-TYPE
			SYNTAX DisplayString
			MAX-ACCESS read-only
			STATUS current
			DESCRIPTION
				"root certificate valid start data."
			::= { rootCertificateDescriptionEntry 4 }

		rootCertificateValidTo OBJECT-TYPE
			SYNTAX DisplayString
			MAX-ACCESS read-only
			STATUS current
			DESCRIPTION
				"root certificate valid end date."
			::= { rootCertificateDescriptionEntry 5 }

		rootCertificateSerialNumber OBJECT-TYPE
			SYNTAX DisplayString
			MAX-ACCESS read-only
			STATUS current
			DESCRIPTION
				"root certificate serial number."
			::= { rootCertificateDescriptionEntry 6 }

		rootCertificateImport OBJECT-TYPE
			SYNTAX DisplayString
			MAX-ACCESS read-write
			STATUS current
			DESCRIPTION
				"Import root certificate,write only. eg:/tmp/cacert.pem"
			::= { rootCertificateDescriptionEntry 7 }

		rootCertificateDelete OBJECT-TYPE
			SYNTAX INTEGER
			MAX-ACCESS read-write
			STATUS current
			DESCRIPTION
				"Information about delete root certificate.
				This vaule will be one of the following:
				(delete(1))."
			::= { rootCertificateDescriptionEntry 8 }

		--client certificate
		clientCertificateDescriptionTable OBJECT-TYPE
			SYNTAX SEQUENCE OF ClientCertificateDescriptionEntry
			MAX-ACCESS not-accessible
			STATUS current
			DESCRIPTION
				"A table containing the list of client certificate information."
			::= { twoFactorAuthentication 51 }

		clientCertificateDescriptionEntry OBJECT-TYPE
			SYNTAX ClientCertificateDescriptionEntry
			MAX-ACCESS not-accessible
			STATUS current
			DESCRIPTION
				"Information about client certificate."
			INDEX { clientCertificateIndex }
			::= { clientCertificateDescriptionTable 1 }

		ClientCertificateDescriptionEntry ::=
			SEQUENCE {
				clientCertificateIndex
					INTEGER,
				clientCertificateFingerPrint
					DisplayString,
				clientCertificateImport
					DisplayString,
				clientCertificateDelete
					INTEGER
				}

		clientCertificateIndex OBJECT-TYPE
			SYNTAX INTEGER
			MAX-ACCESS not-accessible
			STATUS current
			DESCRIPTION
				""
			::= { clientCertificateDescriptionEntry 1 }

		clientCertificateFingerPrint OBJECT-TYPE
			SYNTAX DisplayString
			MAX-ACCESS read-only
			STATUS current
			DESCRIPTION
				"The client certificate finger print."
			::= { clientCertificateDescriptionEntry 2 }

		clientCertificateImport OBJECT-TYPE
			SYNTAX DisplayString
			MAX-ACCESS read-write
			STATUS current
			DESCRIPTION
				"Import client certificate,write only. eg:/tmp/clientcert.pem"
			::= { clientCertificateDescriptionEntry 3 }

		clientCertificateDelete OBJECT-TYPE
			SYNTAX INTEGER
			MAX-ACCESS read-write
			STATUS current
			DESCRIPTION
				"Information about delete client certificate.
				This vaule will be one of the following:
				(delete(1))."
			::= { clientCertificateDescriptionEntry 4 }
			
--    ****** configuration Information *******************************
		configuration OBJECT IDENTIFIER ::= { hwiBMC 42 }
		
		exportconfig OBJECT-TYPE
				SYNTAX DisplayString
				MAX-ACCESS read-write
				STATUS current
				DESCRIPTION
					"Starting to export all configuration of BMC and BIOS.
					 The input parameter is file path or URL of configuration file.
					 Filepath  e.g.: /tmp/config.xml
					 File URL      : protocol://username:password@IP:[port]/directory/filename
						 The parameters in the URL are described as follows:
						 The protocol must be https,sftp,cifs,scp or nfs.
						 The username and password are those of the destination server.
						 The directory and filename are those on the destination server."
				::= { configuration 1 }

		importconfig OBJECT-TYPE
				SYNTAX DisplayString
				MAX-ACCESS read-write
				STATUS current
				DESCRIPTION
					"Starting to import all configuration of BMC and BIOS.
					 The input parameter is file path or URL of configuration file.
					 Filepath  e.g.: /tmp/config.xml
					 File URL      : protocol://username:password@IP:[port]/directory/filename
						 The parameters in the URL are described as follows:
						 The protocol must be https,sftp,cifs,scp or nfs.
						 The username and password are those of the destination server.
						 The directory and filename are those on the destination server."
				::= { configuration 2 }
		
		configprogress OBJECT-TYPE
				SYNTAX DisplayString
				MAX-ACCESS read-only
				STATUS current
				DESCRIPTION
					"Query the progress of exporting/importing all configuration of BMC and BIOS.
					 Query the progress of uploading configuration file to remote host or download configuration file from remote host.
					 The positive value means percentage of exporting/importing or uploading/downloading.
					 The negative value(-1) means error."
				::= { configuration 3 }
		
		configerrorinfo OBJECT-TYPE
				SYNTAX DisplayString
				MAX-ACCESS read-only
				STATUS current
				DESCRIPTION
					"Query the error information of exporting/importing all configuration of BMC and BIOS.
					 Query the error information of uploading configuration file to remote host or download configuration file from remote host.
					 If error happened, configerrorinfo value shows the error information.
					 If error don't happened, configerrorinfo value is null."
				::= { configuration 4 }
			
END
